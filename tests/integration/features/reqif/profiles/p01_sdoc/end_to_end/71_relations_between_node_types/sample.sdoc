[DOCUMENT]
TITLE: sample

[GRAMMAR]
ELEMENTS:
- TAG: NEED
  FIELDS:
  - TITLE: UID
    TYPE: String
    REQUIRED: False
  - TITLE: STATEMENT
    TYPE: String
    REQUIRED: False
- TAG: REQUIREMENT
  FIELDS:
  - TITLE: UID
    TYPE: String
    REQUIRED: False
  - TITLE: STATEMENT
    TYPE: String
    REQUIRED: False
  RELATIONS:
  - TYPE: Parent
    ROLE: Traces

[NEED]
UID: ND-1
STATEMENT: >>>
The operator needs continuous telemetry.
<<<

[REQUIREMENT]
UID: RQ-1
STATEMENT: >>>
The spacecraft shall downlink telemetry at least once per day.
<<<
RELATIONS:
- TYPE: Parent
  VALUE: ND-1
  ROLE: Traces
