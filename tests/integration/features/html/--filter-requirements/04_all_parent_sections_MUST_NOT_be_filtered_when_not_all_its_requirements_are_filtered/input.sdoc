[DOCUMENT]
TITLE: Hello world doc

[REQUIREMENT]
TITLE: Title #1
STATEMENT: Statement #1

[REQUIREMENT]
TITLE: Title #2
STATEMENT: Statement #2

[[SECTION]]
TITLE: MUST_NOT_BE_FILTERED_1

[[SECTION]]
TITLE: MUST_BE_FILTERED_2

[REQUIREMENT]
TITLE: Title #3
STATEMENT: Statement #3

[REQUIREMENT]
TITLE: Title #4
STATEMENT: Statement #4

[[/SECTION]]

[REQUIREMENT]
TITLE: Title #5
STATEMENT: Statement #3

[[/SECTION]]
