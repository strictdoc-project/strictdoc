[DOCUMENT]
TITLE: Document 1

[FREETEXT]
Hello world!
[/FREETEXT]

[REQUIREMENT]
UID: SOME-OTHER-PREFIX-1
TITLE: Requirement title #1
STATEMENT: >>>
Requirement statement #1.
<<<
RATIONALE: >>>
Requirement rationale #1.
<<<

[REQUIREMENT]
UID: REQ-1
TITLE: Requirement title #2
STATEMENT: >>>
Requirement statement #2.
<<<
RATIONALE: >>>
Requirement rationale #2.
<<<

[REQUIREMENT]
UID: REQ-2
TITLE: Requirement title #3
STATEMENT: >>>
Requirement statement #3.
<<<
RATIONALE: >>>
Requirement rationale #3.
<<<
