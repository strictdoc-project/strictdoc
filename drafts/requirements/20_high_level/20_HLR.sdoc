[DOCUMENT]
TITLE: [L2] Requirements Tool specification
REQ_PREFIX: SDOC-SSS-

[SECTION]
TITLE: Overview

[SECTION]
TITLE: Document types

[FREETEXT]
A variety of document types used by the industries. The variety comes from:

- Supporting flexible documentation structures, e.g., non-nested vs. deeply nested.
- Supporting custom fields used by different industries (the criticality levels in various industries, RAIT in aerospace, status/workflow fields, etc.)
- Supporting a rich set of visualization mechanisms.

Examples of document types include:

- Requirements specification
- Design document / architecture description document
- Interface control document / API reference
- User manual
- Development plan
- Systems engineering plan, management plan
- Standard (e.g., ECSS or ISO 26262).
[/FREETEXT]

[/SECTION]

[SECTION]
TITLE: Workflows

[FREETEXT]
TBD

Assist workflows with project requirements and documentations. Integrate with existing workflows



- Document- and table-based workflow
- Requirements analysis and prototyping
- Requirements compliance, traceability and justification

- Requirements implementation:

  - Assisting software engineers in implementing requirements in source code.
  - Making links between requirements and source code implementation units, e.g., files, functions, code fragments.
  - Linking source code implementation units to requirements using special markers left in source code.

- Requirements verification workflow (RAIT)
- Configuration management
- Reporting
- Collaboration on requirements
- Requirements exchange

- Formal reviews:

  - Formal review of documentation
  - Walkthroughs, inspections
  - Version control of delivered documentation packages
  - Assessment of progress reports achieved.

- Interoperability with industry standards

- Integration between distinct projects requirements trees.

  - Examples of integration: An embedded software project has its own requirements. The developers want to integrate a requirements subtree of another product that is integrated to the parent project as an off-the-shelf solution.
[/FREETEXT]

[/SECTION]

[SECTION]
TITLE: Target audience

[FREETEXT]
- Engineering professionals

- Software engineers

  - The tool is close to software engineering workflow, i.e., it has edges to software version control, software IDEs, source code, etc.


- Management
- General audience
[/FREETEXT]

[/SECTION]

[/SECTION]

[SECTION]
UID: SECTION-RTS-Requirements-management
TITLE: Requirements management

[FREETEXT]
TBD:

- Maintain consistency of requirements database
- Requirements writing best practice
[/FREETEXT]

[REQUIREMENT]
UID: SDOC-SSS-4
STATUS: Active
TITLE: Requirements CRUD
STATEMENT: >>>
The Requirements Tool shall enable the main requirements management operations:

Create a requirement
Read / view / browse a requirement
Update / edit a requirement
Delete a requirement.
<<<
RATIONALE: >>>
The CRUD operations are at the core of the requirements management.
<<<

[REQUIREMENT]
UID: SDOC-SSS-61
STATUS: Active
TITLE: Minimal requirement field set
STATEMENT: >>>
The Requirements Tool shall support at least the following requirement field set:

- UID
- STATUS
- TITLE
- STATEMENT
- RATIONALE
- COMMENT
- RELATIONS (connections with other requirements).
<<<
RATIONALE: >>>
The selection of the minimal set is based on what is common in the industries (e.g., automotive, space, etc).
<<<
COMMENT: >>>
The other fields common to each industry can be customized with custom fields handled by other requirements.
<<<
RELATIONS:
- TYPE: Parent
  VALUE: ZEP-10
- TYPE: Parent
  VALUE: ZEP-14

[REQUIREMENT]
UID: SDOC-SSS-62
STATUS: Active
TITLE: Custom fields
STATEMENT: >>>
The requirements tool shall support configuring a requirement item with an arbitrary set of fields.

NOTE: Examples of typical fields include: UID, Title, Statement, Rationale, Comment. Other fields that are used very often are: Status, Tags, Criticality level, Priority, etc.
<<<
RATIONALE: >>>
The tool shall not constrain a user in which fields they are able to use for their projects.
<<<
RELATIONS:
- TYPE: Parent
  VALUE: ZEP-3

[REQUIREMENT]
UID: SDOC-SSS-64
STATUS: Active
TITLE: Structuring requirements in documents
STATEMENT: >>>
The Requirements Tool shall support structuring requirements in documents.
<<<
RATIONALE: >>>
The industry works with requirements documents. The documents have sections/chapters and requirements.
<<<
RELATIONS:
- TYPE: Parent
  VALUE: ZEP-13

[REQUIREMENT]
UID: SDOC-SSS-5
STATUS: Active
TITLE: Move requirement nodes within document
STATEMENT: >>>
The Requirements Tool shall allow moving nodes (sections, requirements) within the containing document.
<<<

[REQUIREMENT]
UID: SDOC-SSS-70
STATUS: Active
TITLE: Move nodes between documents
STATEMENT: >>>
The Requirements Tool shall allow moving nodes (sections, requirements) between documents.
<<<

[REQUIREMENT]
UID: SDOC-SSS-6
STATUS: Active
TITLE: Auto-provision of Requirement UIDs
STATEMENT: >>>
The Requirements Tool shall provide controls for automatic generation of requirements UIDs.
<<<
RATIONALE: >>>
When a document is large, it becomes harder to manage the assignment of the new requirements identifiers by manually exploring which requirement UID has not been assigned yet. The provision of automatically generated UIDs is a convenience feature that improves the user experience significantly.
<<<
RELATIONS:
- TYPE: Parent
  VALUE: ZEP-8

[REQUIREMENT]
UID: SDOC-SSS-7
TITLE: Link requirements together
RELATIONS:
- TYPE: Parent
  VALUE: ZEP-4

[REQUIREMENT]
UID: SDOC-SSS-8
STATUS: Backlog
TITLE: Multiple link roles
STATEMENT: >>>
The Requirements Tool shall support the link roles.

Example of roles for a child-to-parent link: "verifies", "implements", "satisfies", etc.
<<<
RATIONALE: >>>
Different industries maintain custom conventions for naming the relations between requirements and other nodes such as tests or other artefacts.
<<<
RELATIONS:
- TYPE: Parent
  VALUE: ZEP-5

[REQUIREMENT]
UID: SDOC-SSS-71
STATUS: Backlog
TITLE: Reverse parent links
STATEMENT: >>>
The Requirements Tool shall support the Reverse Parent relationship.
<<<

[REQUIREMENT]
UID: SDOC-SSS-47
STATUS: Active
TITLE: Prevent cycles between nodes
STATEMENT: >>>
The Requirements Tool shall provide a validation mechanism that prevents requirement links from forming cycles.
<<<

[REQUIREMENT]
UID: SDOC-SSS-57
STATUS: Active
TITLE: Requirement syntax validation (e.g. EARS)
STATEMENT: >>>
The Requirements Tool shall provide capabilities for validating requirements according to the EARS syntax.
<<<

[/SECTION]

[SECTION]
UID: SECTION-RTS-Documentation-management
TITLE: Documentation management

[FREETEXT]
TBD: Requirements and specifications (plain, non-nested vs deeply nested)

The Requirements Tool shall support a variety of document types used by the industries. The variety comes from:

Supporting flexible documentation structures, e.g., non-nested vs. deeply nested.
Supporting custom fields used by different industries (the criticality levels in various industries, RAIT in aerospace, status/workflow fields, etc.)
Supporting a rich set of visualization mechanisms.

Examples of document types include:

Requirements specification
Design document / architecture description document
Interface control document / API reference
User manual
Development plan, systems engineering plan, management plan
Standard (e.g., ECSS or ISO 26262).

Consistency TBD:

- No (or less) run-away documentation
- Reduce documentation hazards
- Keep documents up-to-date
[/FREETEXT]

[REQUIREMENT]
UID: SDOC-SSS-3
STATUS: Active
TITLE: Documents (CRUD)
STATEMENT: >>>
The Requirements Tool shall provide the CRUD operations for document management:

- Create document
- Read document
- Update document
- Delete document.
<<<
RATIONALE: >>>
The CRUD operations are essential operations of document management. They are at the core of a documentation management tool.
<<<

[REQUIREMENT]
UID: SDOC-SSS-51
STATUS: Active
TITLE: Documents with nested sections/chapters structure
STATEMENT: >>>
The Requirements Tool shall allow management of documents with nested sections/chapters structure.
<<<

[REQUIREMENT]
UID: SDOC-SSS-52
TITLE: Assembling documents from fragments
RELATIONS:
- TYPE: Parent
  VALUE: ZEP-1

[REQUIREMENT]
UID: SDOC-SSS-53
STATUS: Active
TITLE: Document meta information (UID, version, authors, signatures, etc)
STATEMENT: >>>
The Requirements Tool shall support management of document meta information.
<<<

[REQUIREMENT]
UID: SDOC-SSS-75
STATUS: Active
TITLE: Document versioning
STATEMENT: >>>
The Requirements Tool shall provide capabilities for document versioning.
<<<

[REQUIREMENT]
UID: SDOC-SSS-63
TITLE: Text formatting capabilities
STATEMENT: >>>
The Requirements Tool shall provide "rich text" formatting capabilities which includes but not limited to:

- Headings
- Lists
- Tables
- UML diagrams
- etc.
<<<
RELATIONS:
- TYPE: Parent
  VALUE: ZEP-9

[/SECTION]

[SECTION]
UID: SECTION-SSSS-Performance
TITLE: Performance

[REQUIREMENT]
UID: SDOC-SSS-13
STATUS: Active
TITLE: Support large requirements sets
STATEMENT: >>>
The Requirements Tool shall support requirement trees with at least 10000 requirements.
<<<

[REQUIREMENT]
UID: SDOC-SSS-14
STATUS: Active
TITLE: Support large project trees
STATEMENT: >>>
The Requirements Tool shall be able to handle documentation packages of at least 100 documents without significant performance degradation.
<<<

[/SECTION]

[SECTION]
UID: SECTION-SSSS-Existing-workflows
TITLE: Existing workflows

[REQUIREMENT]
UID: SDOC-SSS-73
STATUS: Active
TITLE: Excel-like viewing and editing of requirements
STATEMENT: >>>
The Requirements Tool shall provide an Excel-like user interface for viewing and editing requirements.

NOTE: This interface does not have to be the only or a default interface.
<<<
RATIONALE: >>>
As recognized by the parent requirement, some requirements-based workflows are naturally easier when the requirements content is presented in a form of a table, as opposed to a document with a nested chapter structure.
<<<

[REQUIREMENT]
UID: SDOC-SSS-56
STATUS: Active
TITLE: 1000-feet view
STATEMENT: >>>
The Requirements Tool shall provide a "1000-feet view" kind of requirements visualization.
<<<
RATIONALE: >>>
Compared to the other visualizations, such a visualization helps to "see the forest for the trees". Seeing requirements and their sections all at once helps to visualize groups of requirements and better understand the relationships between them.
<<<

[REQUIREMENT]
UID: SDOC-SSS-28
STATUS: Active
TITLE: Traceability matrices
STATEMENT: >>>
The Requirements Tool shall support generation of traceability matrices.
<<<

[REQUIREMENT]
UID: SDOC-SSS-48
STATUS: Active
TITLE: Compliance matrices
STATEMENT: >>>
The Requirements Tool shall allow generating a Compliance Matrix document.
<<<

[REQUIREMENT]
UID: SDOC-SSS-29
TITLE: Requirements coverage

[REQUIREMENT]
UID: SDOC-SSS-49
STATUS: Active
TITLE: Progress report
STATEMENT: >>>
The Requirements Tool shall allow generating a Progress Report document.

NOTE: A progress report document shall include at least the following Key Performance Indicators.

Project-level KPIs:

- Total number of requirements
- Total number of requirements without parent (excluding top-level and derived)
- Total number of TBD/TBC
- Total number of requirements without rationale
- Tags breakdown

Document-level KPIs: the same but per document.
<<<

[REQUIREMENT]
UID: SDOC-SSS-74
TITLE: Change management
STATEMENT: >>>
The Requirements Tool shall provide capabilities for change management:

- Visualizing changes between project tree versions.
- Visualizing changes between document versions.
- Visualizing the impact that a changed requirement has on a project tree.
<<<

[/SECTION]

[SECTION]
UID: SECTION-RTC-Usability-installation-and-usage
TITLE: Usability, installation and usage

[REQUIREMENT]
UID: SDOC-RMC-8
STATUS: Active
TITLE: General usability
STATEMENT: >>>
The Requirements Tool shall be accessible to a broad spectrum of users.

NOTE: Factors to consider:

- The cost of a tool.
- The easy of installation.
- The availability of a graphical user interface.
- The availability of a programmatic access to the functions of a tool.
- The interoperability of the tool with other tools.
<<<
RATIONALE: >>>
A tool that can be used by a large number of people simplifies its adoption and allows more users to work with documentation and requirements.
<<<

[REQUIREMENT]
UID: SDOC-RMC-9
STATUS: Active
TITLE: Easy user experience
STATEMENT: >>>
The Requirements Tool shall provide a smooth user experience.

NOTE: Documentation and requirements management are composite activities that consist of several types of repetitive tasks. A requirements tool user experience should assist in automating these tasks as far as possible and make the overall workflow efficient and precise.
<<<

[REQUIREMENT]
UID: SDOC-RMC-54
STATUS: Active
TITLE: Support projects with a large number of users
STATEMENT: >>>
The Requirements Tool shall be capable of supporting a large number of users.
<<<
RATIONALE: >>>
Many documentation and requirements projects involve large groups of people. The requirements tool should not become a bottleneck when a number of users grows.
<<<

[REQUIREMENT]
UID: SDOC-RMC-45
STATUS: Active
TITLE: Individual use (home PC)
STATEMENT: >>>
The Requirements Tool shall be usable on the normal personal computers, e.g., do not require a special cloud deployment.
<<<

[REQUIREMENT]
UID: SDOC-RMC-14
STATUS: Active
TITLE: Server-based deployments (IT-friendly setup)
STATEMENT: >>>
The Requirements Tool shall be deployable to the network of computers, e.g., provide a server instance.
<<<
COMMENT: >>>
Scaling from smaller setups (e.g., Raspberry PI in an office network) to
larger in-house and cloud-base installations.
<<<

[REQUIREMENT]
UID: SDOC-RMC-46
STATUS: Active
TITLE: Requirements database
STATEMENT: >>>
The Requirements Tool shall store documentation and requirements data in a database.
<<<
RATIONALE: >>>
A database allows:

- Persistent storage of documentation/requirements data
- Versioning
- Backups
- Exchange of information and access of the same database by multiple users.
<<<

[REQUIREMENT]
UID: SDOC-RMC-47
STATUS: Active
TITLE: Programming access via API (Web)
STATEMENT: >>>
The Requirements Tool shall provide a Web API interface.
<<<
RATIONALE: >>>
Besides a direct access to the tool's source code, accessing an API deployed to a server provides additional capabilities for getting and manipulating requirements/documentation content.
<<<

[REQUIREMENT]
UID: SDOC-RMC-48
STATUS: Active
TITLE: Programming access via API (SDK)
STATEMENT: >>>
The Requirements Tool shall provide a Software Development Kit (SDK) that allows customization of the Requirements Tool functions.

NOTE: An SDK provides access to the API of the Requirements Tool. Examples of functions that may be used by the users of the tool:

- Custom import/export functions to/from various requirements/documentation formats.
- Implement custom visualization functions.
- Implement integration with other tools.
<<<
RATIONALE: >>>
A SDK allows a software engineer to extend the Requirements Tool capabilities.
<<<

[REQUIREMENT]
UID: SDOC-RMC-49
STATUS: Active
TITLE: Programmatic access to requirements data
STATEMENT: >>>
The Requirements Tool shall provide programmatic access to requirements data.
<<<
RATIONALE: >>>
When the requirements data is accessible by a user directly, it is possible to exchange the data or implement additional scripting procedures.
<<<

[/SECTION]

[SECTION]
UID: SECTION-SSSS-Implementation-suggestions
TITLE: Implementation suggestions

[REQUIREMENT]
UID: SDOC-SSS-30
STATUS: Active
TITLE: Static HTML export
STATEMENT: >>>
The Requirements Tool shall support generation of documentation to static HTML.
<<<
RATIONALE: >>>
A static HTML export capability enables:

- Viewing requirements in browsers without any additional software.
- Exchanging HTML content as zip between users.
- Publishing HTML content via static website hosting providers (GitHub and GitLab Pages, Read the Docs, Heroku, etc.).
<<<

[REQUIREMENT]
UID: SDOC-SSS-31
STATUS: Active
TITLE: Web interface
STATEMENT: >>>
The Requirements Tool shall provide a graphical user interface.
<<<

[REQUIREMENT]
UID: SDOC-SSS-32
STATUS: Active
TITLE: Command-line interface
STATEMENT: >>>
The Requirements Tool shall provide a command line interface (CLI).
<<<

[REQUIREMENT]
UID: SDOC-SSS-68
STATUS: Active
TITLE: Web API interface
STATEMENT: >>>
The Requirements Tool shall provide an API interface.
<<<

[REQUIREMENT]
UID: SDOC-SSS-33
STATUS: Active
TITLE: Version control (Git)
STATEMENT: >>>
The Requirements Tool shall support the software version control systems (e.g., Git).
<<<
RATIONALE: >>>
- Git allows precise tracking of the changes to the documentation.
- Requirements/documentation content can be release-tagged.
- The "Time machine" function: ability to review the older state of the documentation/requirements tree.
<<<

[REQUIREMENT]
UID: SDOC-SSS-67
STATUS: Active
TITLE: Support major operating systems
STATEMENT: >>>
The Requirements Tool shall support at least the following operating systems:

- Linux
- Windows
- macOS.
<<<

[REQUIREMENT]
UID: SDOC-SSS-69
STATUS: Active
TITLE: Conservative languages for implementation
STATEMENT: >>>
The Requirements Tool shall be implemented using the popular programming languages.

NOTE: Examples of the most popular programming languages:

- Java
- C++
- Python
- JavaScript
<<<
RATIONALE: >>>
Choosing a less popular programming language can limit the long-term maintainability of the tool.
<<<
COMMENT: >>>
Examples of less popular programming languages, with all due respect to their powerful features: Haskell, F#, Ada, etc.
<<<

[/SECTION]

[SECTION]
UID: SECTION-RTS-Text-based-requirements-language
TITLE: Text-based requirements language (optional)

[FREETEXT]
Note: Not all requirements tools must be text-based. But when they are, the
following requirements apply.
[/FREETEXT]

[REQUIREMENT]
UID: SDOC-SSS-55
STATUS: Active
TITLE: Strict type-safe grammar
STATEMENT: >>>
The Requirements Tool shall provide type safety for its text language.
<<<

[REQUIREMENT]
UID: SDOC-SSS-54
STATUS: Active
TITLE: Machine-readable format
STATEMENT: >>>
The Requirement Tool's text language shall be machine-readable.
<<<
RELATIONS:
- TYPE: Parent
  VALUE: ZEP-2

[REQUIREMENT]
UID: SDOC-SSS-34
STATUS: Active
TITLE: Requirements data from multiple repositories
STATEMENT: >>>
The Requirement Tool shall allow reading requirements files from multiple folders or repositories.

NOTE: The folders/repositories can be arbitrarily nested.
<<<

[/SECTION]

[SECTION]
UID: SECTION-RTS-Requirements-and-source-code
TITLE: Requirements and source code

[REQUIREMENT]
UID: SDOC-SSS-72
STATUS: Active
TITLE: Traceability between requirements and source code
STATEMENT: >>>
The Requirements Tool shall support bi-directional tracing between requirements content and implementation source code.

NOTE: The Requirements Tool does not necessarily have to implement the complete tracing process. It may delegate parts of the traceability task to other tools, e.g., Doxygen, Lobster.
<<<

[/SECTION]

[SECTION]
UID: SECTION-RTS-Requirements-exchange-formats-export-import
TITLE: Requirements exchange formats (export/import)

[FREETEXT]
TBD Barrier-free access to requirements data (easy in, easy out)
[/FREETEXT]

[REQUIREMENT]
UID: SDOC-SSS-58
STATUS: Active
TITLE: ReqIF export/import
STATEMENT: >>>
The Requirements Tool shall support exporting/importing requirements content from/to ReqIF format.
<<<
RATIONALE: >>>
ReqIF is a standard for exchanging requirements. There is currently no other standard of a higher maturity.
<<<
RELATIONS:
- TYPE: Parent
  VALUE: ZEP-6

[REQUIREMENT]
UID: SDOC-SSS-59
STATUS: Active
TITLE: CSV export/import
STATEMENT: >>>
The Requirements Tool shall support exporting/importing requirements content from/to CSV.
<<<
RELATIONS:
- TYPE: Parent
  VALUE: ZEP-7

[REQUIREMENT]
UID: SDOC-SSS-60
STATUS: Active
TITLE: Excel export/import
STATEMENT: >>>
The Requirements Tool shall support exporting/importing requirements content from/to Excel.
<<<

[/SECTION]

[SECTION]
UID: SECTION-RTS-Requirements-collaboration
TITLE: Requirements collaboration

[REQUIREMENT]
UID: SDOC-SSS-65
STATUS: Draft
TITLE: Support user accounts

[REQUIREMENT]
UID: SDOC-SSS-66
STATUS: Draft
TITLE: Send notifications about updated requirements

[/SECTION]

[SECTION]
UID: SECTION-SSSS-Development-process
TITLE: Development process

[REQUIREMENT]
UID: SDOC-SSS-76
STATUS: Active
TITLE: Requirements engineering
STATEMENT: >>>
The Requirements Tool's development process shall include the Requirements Tool's own requirements engineering.
<<<
RATIONALE: >>>
A requirements tool is not a trivial project. A clear set of requirements for the developed tool helps to structure the development and communicate the functions of the tool to the developers and the users of the tool.
<<<

[REQUIREMENT]
UID: SDOC-SSS-50
STATUS: Active
TITLE: Self-hosted requirements
STATEMENT: >>>
The Requirements Tool's requirements shall be developed and stored using the Requirements Tool itself.
<<<
RATIONALE: >>>
While not strictly necessary, developing the requirements for the tool using the tool itself aids developers in test-driving its functionality during the requirement development phase. Moreover, having the tool host its own requirements provides a tangible and dynamic illustration of how the tool can be employed for crafting requirements documentation.
<<<
RELATIONS:
- TYPE: Parent
  VALUE: ZEP-15

[REQUIREMENT]
UID: SDOC-SSS-77
TITLE: Test coverage
STATEMENT: >>>
The Requirements Tool's development process shall ensure:

A testability of the tool
The highest possible coverage of the tool's code by test
Usage of modern testing methods to ensure adequate coverage of the tool's functions (e.g., command-line interface, web interface, smallest units of code, etc.).
<<<
RATIONALE: >>>
The presence of tests, the adequate selection of test methods and a high test coverage are preconditions for a high quality of the requirements tool.
<<<

[REQUIREMENT]
UID: SDOC-SSS-78
STATUS: Active
TITLE: Tool qualification
STATEMENT: >>>
The Requirements Tool's development process shall ensure that the tool can be qualified for the use in critical product developments as required by the rigorous technical standards (e.g., EN IEC 61508).
<<<
RATIONALE: >>>
Many project developments require a qualification of the tools used during the development. A requirements tool is one of the critical tools that affect the project development. If a requirement tool is developed to higher standards of quality, it simplifies the argument of bringing the tool forward and using it in a particular project.
<<<

[/SECTION]

[SECTION]
UID: SECTION-SSSS-Licensing-and-distribution
TITLE: Licensing and distribution

[FREETEXT]
- TBD Direct access to the tool source code
[/FREETEXT]

[REQUIREMENT]
UID: SDOC-SSS-38
STATUS: Active
TITLE: Open source
STATEMENT: >>>
The Requirements Tool's source code shall be publicly available, e.g., hosted on a code hosting platform such as GitHub or GitLab.
<<<

[REQUIREMENT]
UID: SDOC-SSS-39
STATUS: Active
TITLE: Only open source dependencies
STATEMENT: >>>
The Requirement Tool's source code shall be based on open source software components.
<<<

[REQUIREMENT]
UID: SDOC-SSS-40
TITLE: Free

[/SECTION]

[SECTION]
UID: SECTION-RTC-Appendix-A-Document-archetypes
TITLE: Appendix A: Document archetypes

[FREETEXT]
StrictDoc shall support the following document archetypes: **requirements document**
and **specification** document. For both archetypes, StrictDoc shall further
support the following options.

.. list-table:: Table: Requirements and specification document
   :widths: 20 40 40
   :header-rows: 1

   * -
     - Requirements document
     - Specification document
   * - Examples
     - Most typical: requirements lists split by categories (e.g., Functional
       Requirements, Interface Requirements, Performance Requirements, etc.)
     - Often: a standard document
   * - Structure
     - Not nested or not too deeply nested
     - Nested
   * - Visual presentation
     - Requirements are often presented as table cells. Cells can be standalone
       or the whole section or document can be a long table with cells.
     - Requirements are rather presented as header + text
   * - Unique requirement identifiers (UID)
     - Most always
     - - Present or not
       - **NOT SUPPORTED YET:** Can be missing, the chapter headers are used instead.
         The combination "Number + Title" becomes a reference-able identifier.
         A possible intermediate solution when modeling such a document is to
         make the UIDs map to the section number.
   * - Requirement titles
     - - Often
       - **NOT SUPPORTED YET:** But maybe absent (ex: NASA cFS SCH). If absent,
         the grouping is provided by sections.
     - Requirement titles are most often section titles
   * - Real-world examples
     - - NASA cFE Functional Requirements
       - MISRA C coding guidelines,
       - NASA Software Engineering Requirements NPR 7150.2
     - - ECSS Software ECSS-E-ST-40C
[/FREETEXT]

[/SECTION]
