[DOCUMENT]
TITLE: Document 1

[TEXT]
STATEMENT: >>>
Document free text.
<<<

[[SECTION]]
TITLE: Section title

[TEXT]
UID: TEXT-NODE-1
STATEMENT: >>>
Text statement.
<<<

[REQUIREMENT]
TITLE: Requirement title
STATEMENT: >>>
Requirement statement.
<<<

[[/SECTION]]
