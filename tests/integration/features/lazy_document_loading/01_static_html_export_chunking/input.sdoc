[DOCUMENT]
TITLE: Lazy Chunking Doc

[REQUIREMENT]
UID: REQ-001
TITLE: Requirement 001
STATEMENT: >>>
Statement of requirement 001
<<<

[REQUIREMENT]
UID: REQ-002
TITLE: Requirement 002
STATEMENT: >>>
Statement of requirement 002
<<<

[REQUIREMENT]
UID: REQ-003
TITLE: Requirement 003
STATEMENT: >>>
Statement of requirement 003
<<<

[REQUIREMENT]
UID: REQ-004
TITLE: Requirement 004
STATEMENT: >>>
Statement of requirement 004
<<<

[REQUIREMENT]
UID: REQ-005
TITLE: Requirement 005
STATEMENT: >>>
Statement of requirement 005
<<<

[REQUIREMENT]
UID: REQ-006
TITLE: Requirement 006
STATEMENT: >>>
Statement of requirement 006
<<<

[REQUIREMENT]
UID: REQ-007
TITLE: Requirement 007
STATEMENT: >>>
Statement of requirement 007
<<<

[REQUIREMENT]
UID: REQ-008
TITLE: Requirement 008
STATEMENT: >>>
Statement of requirement 008
<<<

[REQUIREMENT]
UID: REQ-009
TITLE: Requirement 009
STATEMENT: >>>
Statement of requirement 009
<<<

[REQUIREMENT]
UID: REQ-010
TITLE: Requirement 010
STATEMENT: >>>
Statement of requirement 010
<<<

[REQUIREMENT]
UID: REQ-011
TITLE: Requirement 011
STATEMENT: >>>
Statement of requirement 011
<<<

[REQUIREMENT]
UID: REQ-012
TITLE: Requirement 012
STATEMENT: >>>
Statement of requirement 012
<<<

[REQUIREMENT]
UID: REQ-013
TITLE: Requirement 013
STATEMENT: >>>
Statement of requirement 013
<<<

[REQUIREMENT]
UID: REQ-014
TITLE: Requirement 014
STATEMENT: >>>
Statement of requirement 014
<<<

[REQUIREMENT]
UID: REQ-015
TITLE: Requirement 015
STATEMENT: >>>
Statement of requirement 015
<<<

[REQUIREMENT]
UID: REQ-016
TITLE: Requirement 016
STATEMENT: >>>
Statement of requirement 016
<<<

[REQUIREMENT]
UID: REQ-017
TITLE: Requirement 017
STATEMENT: >>>
Statement of requirement 017
<<<

[REQUIREMENT]
UID: REQ-018
TITLE: Requirement 018
STATEMENT: >>>
Statement of requirement 018
<<<

[REQUIREMENT]
UID: REQ-019
TITLE: Requirement 019
STATEMENT: >>>
Statement of requirement 019
<<<

[REQUIREMENT]
UID: REQ-020
TITLE: Requirement 020
STATEMENT: >>>
Statement of requirement 020
<<<

[REQUIREMENT]
UID: REQ-021
TITLE: Requirement 021
STATEMENT: >>>
Statement of requirement 021
<<<

[REQUIREMENT]
UID: REQ-022
TITLE: Requirement 022
STATEMENT: >>>
Statement of requirement 022
<<<

[REQUIREMENT]
UID: REQ-023
TITLE: Requirement 023
STATEMENT: >>>
Statement of requirement 023
<<<

[REQUIREMENT]
UID: REQ-024
TITLE: Requirement 024
STATEMENT: >>>
Statement of requirement 024
<<<

[REQUIREMENT]
UID: REQ-025
TITLE: Requirement 025
STATEMENT: >>>
Statement of requirement 025
<<<
