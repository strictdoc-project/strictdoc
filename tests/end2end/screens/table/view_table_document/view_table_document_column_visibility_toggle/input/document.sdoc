[DOCUMENT]
TITLE: Document

[REQUIREMENT]
TITLE: First requirement
STATEMENT: Statement of the first requirement.

[REQUIREMENT]
TITLE: Second requirement
STATEMENT: Statement of the second requirement.
