[DOCUMENT]
TITLE: Document 1

[FREETEXT]
Hello world!
[/FREETEXT]

[REQUIREMENT]
TITLE: Requirement title
STATEMENT: >>>
Requirement statement.
<<<
RATIONALE: >>>
Requirement rationale.
<<<
COMMENT: >>>
Comment #1
<<<
COMMENT: >>>
Comment #2
<<<
COMMENT: >>>
Comment #3
<<<
