[DOCUMENT]
TITLE: Document 1

[FREETEXT]
Modified free text!

[ANCHOR: AD1]
[/FREETEXT]

[SECTION]
TITLE: First title

[FREETEXT]
This is a free text of the first section.

[LINK: AD1]
[/FREETEXT]

[/SECTION]
