[DOCUMENT]
MID: a434bc71a7324efaaed7f5a58e56e544
TITLE: F.A.Q.
UID: SDOC_FAQ
VERSION: Git commit: @GIT_VERSION, Git branch: @GIT_BRANCH
DATE: @GIT_COMMIT_DATETIME
OPTIONS:
  ENABLE_MID: True
  VIEW_STYLE: Inline
  NODE_IN_TOC: True

[GRAMMAR]
ELEMENTS:
- TAG: SECTION
  PROPERTIES:
    IS_COMPOSITE: True
    VIEW_STYLE: Narrative
  FIELDS:
  - TITLE: MID
    TYPE: String
    REQUIRED: False
  - TITLE: UID
    TYPE: String
    REQUIRED: False
  - TITLE: TITLE
    TYPE: String
    REQUIRED: True
- TAG: TEXT
  PROPERTIES:
    VIEW_STYLE: Narrative
  FIELDS:
  - TITLE: MID
    TYPE: String
    REQUIRED: False
  - TITLE: STATEMENT
    TYPE: String
    REQUIRED: True
  RELATIONS:
  - TYPE: Parent
  - TYPE: File

[TEXT]
MID: 5acdfccd5771492f95b70328bd599cf7
STATEMENT: >>>
This document is a list of questions that people ask about StrictDoc.

Missing a question or an answer? Ask it here: [LINK: SDOC_UG_CONTACT].
<<<

[[SECTION]]
MID: e972c79015524961863e095280a81aab
TITLE: What is StrictDoc?

[TEXT]
MID: d8d92e4eb8254cbda8dcb37709a9df45
STATEMENT: >>>
StrictDoc is software for writing technical requirements specifications.

StrictDoc is a spare-time open-source project developed by Stanislav Pankevich
(@stanislaw) and Maryna Balioura (@mettta) with contributions from the Open
Source community.

The project exists since mid-2019.

For a quick overview of the project, check out the
`StrictDoc project <https://github.com/strictdoc-project/strictdoc/blob/main/about/StrictDoc.pdf>`_
slide deck.
<<<

[[/SECTION]]

[[SECTION]]
MID: 86827c92ec3a493d8a2382b75b5277a8
TITLE: Resources about StrictDoc

[[SECTION]]
MID: f7083cf6a84e4b858b5e551f8c8a555a
TITLE: Presentations

[TEXT]
MID: 52342105083e4f80884959d4ca7f4dba
STATEMENT: >>>
1\)
`StrictDoc project <https://github.com/strictdoc-project/strictdoc/blob/main/about/StrictDoc.pdf>`_

This slide deck provides a concise overview of the project, including its goals,
real-world case studies, the motivation behind its creation, implementation
details, and the development roadmap.

2\)
`WHAT-WHY-HOW. A practical model for understanding software requirements <https://github.com/strictdoc-project/strictdoc/blob/main/about/2026_WHAT_WHY_HOW_model.pdf>`_

Training material from a small introductory course on requirements and systems
engineering, presented as an
`ELISA webinar <https://elisa.tech/category/seminar-series/>`_. This webinar
serves as an introduction to the actual requirements engineering training.

Link to the video recording:
`WHAT-WHY-HOW: A practical model for understanding software requirements | ELISA Seminar
<https://youtu.be/tLwLxkhWl90?si=JWOTACOTOUi6L9Nr>`_.

3\)
`Achieving end-to-end traceability in software projects using open source tools (2025) <https://github.com/strictdoc-project/strictdoc/blob/main/about/2025_ESA_SW_Product_Assurance_Workshop.pdf>`_

This is a short presentation about StrictDoc, delivered at the ESA Software
Product Assurance Workshop 2025.

4\) `Exploring possibilities for integrating StrictDoc and ELISA’s requirements
template approach for the Linux kernel' <https://lpc.events/event/19/contributions/2198/attachments/1884/4056/Linux%20Requirements%20with%20StrictDoc.pdf>`_

The talk argues that ELISA's Linux kernel safety documentation model and
StrictDoc's requirements tooling are largely compatible and could be unified,
with StrictDoc filling remaining gaps like drift detection and ELISA adopting it
as a reference tool.

5\)
`Integrating StrictDoc with ELISA's Linux kernel requirements approach - ELISA Project Workshop 2025 <https://www.youtube.com/watch?v=f5v6q3OFv88>`_

The talk introduces the StrictDoc project, demonstrates a traceability use case
at Linutronix, and provides a hands-on showcase of how StrictDoc could support
structured, maintainable requirements workflows for the Linux kernel. The
session explores how requirements engineering practices can be enhanced within
the kernel ecosystem, with an emphasis on improving traceability, documentation
quality, and alignment with ELISA's requirements template approach.

6\)
`Application of the SPDX Safety Profile in the Safety Scope of the Zephyr Project (2024) <https://ftp.fau.de/fosdem/2024/k4401/fosdem-2024-3211-application-of-the-spdx-safety-profile-in-the-safety-scope-of-the-zephyr-project.mp4>`_

This presentation introduces the SPDX Safety Profile and details its application
within the context of the Zephyr Project. There is also a presentation of the
Zephyr project's methodology for capturing requirements using StrictDoc and a
discussion of the upcoming plans for the integration of SPDX into StrictDoc.
<<<

[[/SECTION]]

[[SECTION]]
MID: d22b63a405264a6a80d4ab3f9b2bf9c5
TITLE: Blog posts

[TEXT]
MID: b2f5aea77e504ee1b64a67be24bd3c58
STATEMENT: >>>
1\)
`From Code to Compliance – Part1: IEC 62443 Certification with Industrial Grade Linux Operating System <https://www.linutronix.de/blog/From-Code-to-Compliance-Part1-IEC-62443-Certification-with>`_
by Linutronix.

The blog post outlines how Linutronix achieved security certification for
Linux-based industrial software, with StrictDoc serving as an important building
block in their development workflow.

2\)
`Requirement Traceability with All Substance and No Fuss <https://www.bugseng.com/requirement-traceability-with-all-substance-and-no-fuss/>`_
by BUGSENG.
<<<

[[/SECTION]]

[[SECTION]]
MID: d75bd4d35b4b425b90ec8667ffffe191
TITLE: Screencasts / tutorials

[TEXT]
MID: 9d23e77aa7f848cb8efca49f5cf41f77
STATEMENT: >>>
`Automotive SPICE in opensource StrictDoc tool, with System Architecure ideas <https://www.youtube.com/watch?v=k2MCFWvCs7E>`_
by Lukasz Juranek.
<<<

[[/SECTION]]

[[/SECTION]]

[[SECTION]]
MID: 74235945ec4a4116aecbc883ffba54b7
TITLE: Which web server is recommended for StrictDoc documentation?

[TEXT]
MID: 966a5c3babf84fc7a1454b2799d13470
STATEMENT: >>>
This question can be answered in two ways. First of all, StrictDoc has its own
web server that can be run with ``strictdoc server ...``. Refer to the User
Guide for further information.

The following suggestions assume that you are looking to using a web server to
host the StrictDoc's static HTML export, without using StrictDoc's own web
server.

Is your project public or private? If it is public, you could simply use
`GitHub pages <https://pages.github.com>`_. See how one user of StrictDoc is
doing it here:
`nmfta-repo/vcr-experiment <https://github.com/nmfta-repo/vcr-experiment>`_ and
the resulting static website:
`nmfta-repo.github.io/vcr-experiment <https://nmfta-repo.github.io/vcr-experiment>`_.

A very good alternative to GitHub pages is
`Read the Docs <https://readthedocs.org>`_.

If the project is private, you could use any server that reads HTML files from a
folder. For example, Python has an embedded Web Server, see
`this for example <https://pythonbasics.org/webserver>`_. Also you could try any
web server based on Node.JS.
<<<

[[/SECTION]]

[[SECTION]]
MID: 2e911dedb13348bf827f078bbbca44f4
TITLE: Is StrictDoc compatible with Sphinx?

[TEXT]
MID: ac35a712b4a84f4ab2b61feb15c1550d
STATEMENT: >>>
StrictDoc is only partially compatible with Sphinx.

StrictDoc does not have Sphinx in its dependency tree, and it does not use any
of Sphinx API. Instead, StrictDoc uses Docutils for RST markup support. Using
Docutils, StrictDoc can generate SDoc files to RST files.

There are users of StrictDoc who use both StrictDoc and Sphinx. The following
workflow is known to work:

- Write some documentation in SDoc files.
- Export an SDoc documentation tree to an RST documentation tree.
- Connect RST documentation tree with a Sphinx setup.
- Run Sphinx against an RST documentation tree, obtain a Sphinx documentation
  website or LaTex PDF.

There is a GitHub issue
`Unexpected restriction on specific RST directives / compatibility with Breathe Sphinx Plugin #1093 <https://github.com/strictdoc-project/strictdoc/issues/1093>`_
where a closer bridging between StrictDoc and Sphinx was discussed with no
specific and actionable outcome. This comment is
`especially relevant <https://github.com/strictdoc-project/strictdoc/issues/1093#issuecomment-1505108384>`_
as well as the one about a
`possible implementation <https://github.com/strictdoc-project/strictdoc/issues/1093#issuecomment-1545599711>`_.
<<<

[[/SECTION]]

[[SECTION]]
MID: 235122d2c10748918c7c6ff736e39d18
UID: SECTION-FAQ-How-did-the-SDoc-text-language-become-what-it-is
TITLE: How did the SDoc text language become what it is?

[TEXT]
MID: b3561dd4f8e64f11a251c3471022aece
STATEMENT: >>>
See [LINK: SECTION-FM-SDoc-text-markup] for a description of the SDoc feature.
<<<

[[/SECTION]]

[[SECTION]]
MID: 1d4220cc9a5444a5bdbaee91c8c50670
TITLE: How StrictDoc compares to other tools?

[TEXT]
MID: 45093addf6ec4772a0289fd958ae61dc
STATEMENT: >>>
This section compares some requirements management tools that are similar to
StrictDoc.
<<<

[[SECTION]]
MID: a4533ae81bfe446295242add9156198e
TITLE: Doorstop

[TEXT]
MID: d0c305180d8747a1b70254eaf2c4f201
STATEMENT: >>>
The StrictDoc project is a close successor of another project called
`Doorstop <https://github.com/doorstop-dev/doorstop>`_.

    Doorstop is a requirements management tool that facilitates the storage of
    textual requirements alongside source code in version control.

The author of Doorstop has published a
`paper about Doorstop <http://www.scirp.org/journal/PaperInformation.aspx?PaperID=44268#.UzYtfWRdXEZ>`_
where the rationale behind text-based requirements management is provided.

The first version of StrictDoc had started as a fork of the Doorstop project.
However, after a while, the StrictDoc was started from scratch as a separate
project. At this point, StrictDoc and Doorstop do not share any code but
StrictDoc still shares with Doorstop their common underlying design principles:

- Both Doorstop and StrictDoc are written using Python. Both are pip packages which are easy-to-install.
- Both Doorstop and StrictDoc provide a command-line interface.
- Both Doorstop and StrictDoc use text files for requirements management.
- Both Doorstop and StrictDoc encourage collocation of code and documentation.
  When documentation is hosted close to code it has less chances of diverging
  from the actual implementation or becoming outdated.

StrictDoc differs from Doorstop in a number of aspects:

- Doorstop stores requirements in YAML files, one separate file per requirement
  (`example <https://github.com/doorstop-dev/doorstop/blob/804153c67c7c5466ee94e9553118cc3df03a56f9/reqs/REQ001.yml>`_).
  The document in Doorstop is assembled from the requirements files into a
  single logical document during the document generation process.
  StrictDoc's documentation unit is one document stored in an .sdoc file. Such a
  document can have multiple requirements grouped by sections.
- In YAML files, Doorstop stores requirements properties such as
  ``normative: true`` or ``level: 2.3`` for which Doorstop provides validations.
  Such a design decision, in fact, assumes an existence of implicitly-defined
  grammar which is encoded "ad-hoc" in the parsing and validation rules of
  Doorstop.
  StrictDoc takes a different approach and defines its grammar explicitly using
  a tool for creating Domain-Specific Languages called `textX <https://github.com/textX/textX>`_.
  TextX support allows StrictDoc to encode a strict type-safe grammar in a
  `single grammar file <https://github.com/strictdoc-project/strictdoc/blob/93486a0e9fb30b141187587eae9e995cd86c6cbf/strictdoc/backend/dsl/grammar.py>`_
  that StrictDoc uses to parse the documentation files
  using the parsing capabilities provided by textX out of the box.

The roadmap of StrictDoc contains a work item for supporting the export/import
to/from Doorstop format.
<<<

[[/SECTION]]

[[SECTION]]
MID: 5012af516d18447caa3a2dbce97d3e4a
TITLE: Sphinx

[TEXT]
MID: 74b6be0dc2bb485987d8731348cdf5ce
STATEMENT: >>>
Both Sphinx and StrictDoc are both documentation generators but StrictDoc is at
a higher level of abstraction: StrictDoc's specialization is requirements and
specifications documents. StrictDoc can generate documentation to a number of
formats including HTML format as well as the RST format which is a default
input format for Sphinx.

A two-stage generation is therefore possible: StrictDoc generates RST
documentation which then can be generated to HTML, PDF, and other formats using
Sphinx.

This documentation itself (the website you may currently be reading at
https://strictdoc.readthedocs.io) is generated directly by StrictDoc's HTML
and PDF (HTML2PDF) exports, without going through RST or Sphinx.
<<<

[[/SECTION]]

[[SECTION]]
MID: 723731c256fc43dfb315a300f6429945
TITLE: Other tools

[TEXT]
MID: ad24dca8ed9c449ab76c1798f38eb37c
STATEMENT: >>>
See also this GitHub gist for an overview of more tools available on GitHub:
https://gist.github.com/stanislaw/aa40eb7de9f522ad482e5d239c435ff8.
<<<

[[/SECTION]]

[[/SECTION]]

[[SECTION]]
MID: ff143a18e98144bd86e10e29616c187b
TITLE: How long has the StrictDoc project been around?

[TEXT]
MID: 47d60404cf574aebb8c83795589c4137
STATEMENT: >>>
The Development Plan contains the current roadmap:
[LINK: SECTION-DP-Roadmap-diagram].

Below is a brief chronology of StrictDoc's early years of development until the
end of 2022.

----

The first StrictDoc commit dates back to ``2019-08-10``.

**2019 – July – August**

StrictDoc is a result of several attempts to find a solution for working with
text-based requirements. The first version of StrictDoc had started as a fork of
the Doorstop project. However, after a while, StrictDoc was started from scratch
as a separate project.

**2019 – August**

StrictDoc, first generation, the first commit dates to ``2019-08-10``.
Markdown-based C++ program. Custom requirements metadata in YAML.

**2020 – January**

StrictDoc, second generation: RST/Sphinx-based Python program. Using Sphinx
extensions to manage meta information. First integration tests.

**2020 – May**

The current StrictDoc repository was created on GitHub: the first commit dates
back ``2020-05-14``. The code still uses RST for parsing requirements meta
information and PySide for GUI.

The result of these efforts was the realization that a text-based requirements
and specifications management tool could be built on top of a domain-specific
language (DSL) created specifically for the purpose of writing requirements and
specifications documents. Such a language allows explicit definition of a
document data model which is called "grammar".

**2020 – July**

The custom RST parser was replaced with a TextX-based DSL. Since then, StrictDoc
has been using TextX for parsing SDoc files. The new StrictDoc grammar was
created. A simple export to HTML with Jinja templates replaced the PySide GUI.
Export to Sphinx HTML/PDF was introduced.

**2020 – Q4**

Improvements in the styles of HTML/PDF exports. First Table, Traceability, and
Deep Traceability screens.

**2021 – Q1**

Excel export. The first implementation of forward and reverse traceability
between SDoc and source files.

**2021 – Q2**

Further work on the SDoc-source traceability.

**2021 – Q3**

Further work on the SDoc-source traceability. Tree cycles detection,
validations. MathJax support.

**2021 – Q4**

Improvements of the traceability index generation and validation. Initial
implementation of ReqIF. First support of custom grammars.

**2022 – Q1**

Further work on ReqIF and custom grammars. Document fragments feature.

**2022 – Q2**

Excel conversion improvements. Improvements of how meta information is
displayed in HTML export.

**2022 – Q3**

No work in this quarter.

**2022 – Q4**

Installation using PyInstaller. The first prototype of a Web-based interface.
First end-to-end Web tests using SeleniumBase. Improvements of the ReqIF
support.
<<<

[[/SECTION]]

[[SECTION]]
MID: 6e5ed6bb36634220a0c583d21c96295f
TITLE: Which StrictDoc statistics are available?

[TEXT]
MID: 730bfedff6b24c34a6d6331051fd76d3
STATEMENT: >>>
Most relevant GitHub statistics:

- `StrictDoc contributors <https://github.com/strictdoc-project/strictdoc/graphs/contributors>`_

- The `pip trends <https://piptrends.com>`_ helps to visualize the Pip package
  download stats.

  - The ``reqif`` satellite project is included for comparison as well: `strictdoc vs reqif <https://piptrends.com/compare/strictdoc-vs-reqif>`_.

- `Known StrictDoc issues <https://github.com/strictdoc-project/strictdoc/issues?q=is%3Aissue%20state%3Aopen%20type%3ABug>`_
<<<

[[/SECTION]]
