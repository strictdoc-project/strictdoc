[DOCUMENT]
TITLE: Document with two nested sections

[SECTION]
TITLE: Section #1

[SECTION]
TITLE: Section #1.1

[REQUIREMENT]
UID: REQ-1.1.1
STATEMENT: The mapping function shall map requirement_ID to UID.

[REQUIREMENT]
UID: REQ-1.1.2
STATEMENT: The mapping function shall map requirement_ID to UID.

[/SECTION]

[SECTION]
TITLE: Section #1.2

[REQUIREMENT]
UID: REQ-1.2.1
STATEMENT: The mapping function shall map requirement_ID to UID.

[REQUIREMENT]
UID: REQ-1.2.2
STATEMENT: The mapping function shall map requirement_ID to UID.

[/SECTION]

[/SECTION]

[SECTION]
TITLE: Section #2

[SECTION]
TITLE: Section #2.1

[REQUIREMENT]
UID: REQ-2.1.1
STATEMENT: The mapping function shall map requirement_ID to UID.

[REQUIREMENT]
UID: REQ-2.1.2
STATEMENT: The mapping function shall map requirement_ID to UID.

[/SECTION]

[SECTION]
TITLE: Section #2.2

[REQUIREMENT]
UID: REQ-2.2.1
STATEMENT: The mapping function shall map requirement_ID to UID.

[REQUIREMENT]
UID: REQ-2.2.2
STATEMENT: The mapping function shall map requirement_ID to UID.

[/SECTION]

[/SECTION]
