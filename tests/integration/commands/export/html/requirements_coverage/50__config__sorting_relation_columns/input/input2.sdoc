[DOCUMENT]
TITLE: Hello world doc #2

[GRAMMAR]
ELEMENTS:
- TAG: REQUIREMENT
  FIELDS:
  - TITLE: UID
    TYPE: String
    REQUIRED: True
  - TITLE: TITLE
    TYPE: String
    REQUIRED: True
  - TITLE: STATEMENT
    TYPE: String
    REQUIRED: True
  RELATIONS:
  - TYPE: Parent

[REQUIREMENT]
UID: REQ2-001
TITLE: LLRequirement Title #1
STATEMENT: Requirement Statement #1

[REQUIREMENT]
UID: REQ2-002
TITLE: LLRequirement Title #2
STATEMENT: Requirement Statement #2

[REQUIREMENT]
UID: REQ2-003
TITLE: LLRequirement Title #3
STATEMENT: Requirement Statement #3
