[DOCUMENT]
TITLE: Document 1

[GRAMMAR]
ELEMENTS:
- TAG: TEXT
  FIELDS:
  - TITLE: UID
    TYPE: String
    REQUIRED: False
  - TITLE: STATEMENT
    TYPE: String
    REQUIRED: True
- TAG: SECTION
  PROPERTIES:
    IS_COMPOSITE: True
    PREFIX: FOO-
  FIELDS:
  - TITLE: MID
    TYPE: String
    REQUIRED: False
  - TITLE: UID
    TYPE: String
    REQUIRED: False
  - TITLE: TITLE
    TYPE: String
    REQUIRED: False
- TAG: REQUIREMENT
  FIELDS:
  - TITLE: MID
    TYPE: String
    REQUIRED: False
  - TITLE: UID
    TYPE: String
    REQUIRED: False
  - TITLE: TITLE
    TYPE: String
    REQUIRED: False
  - TITLE: STATEMENT
    TYPE: String
    REQUIRED: False
  - TITLE: RATIONALE
    TYPE: String
    REQUIRED: False

[[SECTION]]
TITLE: Section

[REQUIREMENT]
UID: FOO-1
TITLE: Requirement title #1
STATEMENT: >>>
Requirement statement #1.
<<<
RATIONALE: >>>
Requirement rationale #1.
<<<

[REQUIREMENT]
UID: FOO-2
TITLE: Requirement title #2
STATEMENT: >>>
Requirement statement #2.
<<<
RATIONALE: >>>
Requirement rationale #2.
<<<

[[/SECTION]]
