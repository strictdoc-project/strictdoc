[DOCUMENT]
TITLE: Hello world doc
PREFIX: DOC-

[[SECTION]]
PREFIX: LEVEL1-REQ-
TITLE: Section 1

[REQUIREMENT]
UID: LEVEL1-REQ-1
STATEMENT: System shall do L1-1.

[REQUIREMENT]
UID: LEVEL1-REQ-2
STATEMENT: System shall do L1-1.

[[/SECTION]]

[[SECTION]]
PREFIX: LEVEL2-REQ-
TITLE: Section 2

[REQUIREMENT]
UID: LEVEL2-REQ-2
STATEMENT: System shall do L2-1.

[REQUIREMENT]
UID: LEVEL2-REQ-1
STATEMENT: System shall do L2-1.

[[/SECTION]]
