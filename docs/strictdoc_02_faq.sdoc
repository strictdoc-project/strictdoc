[DOCUMENT]
MID: a434bc71a7324efaaed7f5a58e56e544
TITLE: F.A.Q.
UID: SDOC_FAQ
OPTIONS:
  ENABLE_MID: True
  REQUIREMENT_STYLE: Inline
  REQUIREMENT_IN_TOC: True

[GRAMMAR]
ELEMENTS:
- TAG: TEXT
  FIELDS:
  - TITLE: MID
    TYPE: String
    REQUIRED: False
  - TITLE: STATEMENT
    TYPE: String
    REQUIRED: True
  RELATIONS:
  - TYPE: Parent
  - TYPE: File

[TEXT]
MID: 5acdfccd5771492f95b70328bd599cf7
STATEMENT: >>>
This document is a list of questions that people ask about StrictDoc.

Missing a question or an answer? Ask it here: [LINK: SDOC_UG_CONTACT].
<<<

[SECTION]
MID: e972c79015524961863e095280a81aab
TITLE: What is StrictDoc?

[TEXT]
MID: d8d92e4eb8254cbda8dcb37709a9df45
STATEMENT: >>>
StrictDoc is software for writing technical requirements specifications.

StrictDoc is a spare-time open-source project developed by Stanislav Pankevich (@stanislaw) and Maryna Balioura (@mettta) with contributions from the Open Source community.

The project exists since mid-2019.
<<<

[/SECTION]

[SECTION]
MID: 86827c92ec3a493d8a2382b75b5277a8
TITLE: Resources about StrictDoc

[TEXT]
MID: 2ba0c8fa79604b708927ffed2ef94664
STATEMENT: >>>
Talks:

- `Application of the SPDX Safety Profile in the Safety Scope of the Zephyr Project <https://mirrors.dotsrc.org/fosdem/2024/k4401/fosdem-2024-3211-application-of-the-spdx-safety-profile-in-the-safety-scope-of-the-zephyr-project.mp4>`_. This presentation introduces the SPDX Safety Profile and details its application within the context of the Zephyr Project. There is also a presentation of the Zephyr project's methodology for capturing requirements using StrictDoc and a discussion of the upcoming plans for the integration of SPDX into StrictDoc.

Blog posts:

- `Requirement Traceability with All Substance and No Fuss
  <https://www.bugseng.com/blog/requirement-traceability-all-substance-and-no-fuss>`_
  by BUGSENG.

Screencasts/tutorials:

- `Automotive SPICE in opensource StrictDoc tool, with System Architecure ideas
  <https://www.youtube.com/watch?v=k2MCFWvCs7E>`_
  by Lukasz Juranek.
<<<

[/SECTION]

[SECTION]
MID: 74235945ec4a4116aecbc883ffba54b7
TITLE: Which web server is recommended for StrictDoc documentation?

[TEXT]
MID: 966a5c3babf84fc7a1454b2799d13470
STATEMENT: >>>
This question can be answered in two ways. First of all, StrictDoc has its own web server that can be run with ``strictdoc server ...``. Refer to the User Guide for further information.

The following suggestions assume that you are looking to using a web server to host the StrictDoc's static HTML export, without using StrictDoc's own web server.

Is your project public or private? If it is public, you could simply use `GitHub pages <https://pages.github.com>`_. See how one user of StrictDoc is doing it here: `nmfta-repo/vcr-experiment <https://github.com/nmfta-repo/vcr-experiment>`_ and the resulting static website: `nmfta-repo.github.io/vcr-experiment <https://nmfta-repo.github.io/vcr-experiment>`_.

A very good alternative to GitHub pages is `Read the Docs <https://readthedocs.org>`_.

If the project is private, you could use any server that reads HTML files from a folder. For example, Python has an embedded Web Server, see `this for example <https://pythonbasics.org/webserver>`_. Also you could try any web server based on Node.JS.
<<<

[/SECTION]

[SECTION]
MID: 2e911dedb13348bf827f078bbbca44f4
TITLE: Is StrictDoc compatible with Sphinx?

[TEXT]
MID: ac35a712b4a84f4ab2b61feb15c1550d
STATEMENT: >>>
StrictDoc is only partially compatible with Sphinx.

StrictDoc does not have Sphinx in its dependency tree, and it does not use any of Sphinx API. Instead, StrictDoc uses Docutils for RST markup support. Using Docutils, StrictDoc can generate SDoc files to RST files.

There are users of StrictDoc who use both StrictDoc and Sphinx. The following workflow is known to work:

- Write some documentation in SDoc files.
- Export an SDoc documentation tree to an RST documentation tree.
- Connect RST documentation tree with a Sphinx setup.
- Run Sphinx against an RST documentation tree, obtain a Sphinx documentation website or LaTex PDF.

There is a GitHub issue `Unexpected restriction on specific RST directives / compatibility with Breathe Sphinx Plugin #1093 <https://github.com/strictdoc-project/strictdoc/issues/1093>`_ where a closer bridging between StrictDoc and Sphinx was discussed with no specific and actionable outcome. This comment is `especially relevant <https://github.com/strictdoc-project/strictdoc/issues/1093#issuecomment-1505108384>`_ as well as the one about `possible implementation <https://github.com/strictdoc-project/strictdoc/issues/1093#issuecomment-1545599711>`_.
<<<

[/SECTION]

[SECTION]
MID: 235122d2c10748918c7c6ff736e39d18
TITLE: How did the SDoc text language become what it is?

[TEXT]
MID: b3561dd4f8e64f11a251c3471022aece
STATEMENT: >>>
Shortly: The SDoc markup is a hybrid of TOML and YAML with some influence from HTML/XML and `ASN.1 <https://en.wikipedia.org/wiki/ASN.1>`_. Using each of these formats as-is, and also the JSON format, was considered but discarded during the design. The SDoc markup has been pretty stable since its inception but the flexibility of the TextX parser allows easy modifications of the language in case of future evolutions. Any feedback to the current design of the markup language is appreciated.

----

The main use case for SDoc is to model a structure of a technical document that consists of tens and hundreds of technical requirements. The following high-level requirements for the markup are therefore relevant:

- Encode documents of reasonable size (up to several hundreds or few thousands of A4-printed pages).
- Visualize large blocks of requirements text without too much markup noise.
- Support documents with nested (2-4 levels) or deeply nested structure (detailed technical specifications with up to 9-10 levels of chapter nesting).
- Support multiple fields for requirement meta information which makes a requirement look like "a text with some meta information around it".

SDoc format is inspired by several formats: TOML, YAML, ASN.1 and HTML/XML.

**TOML: Square bracket syntax**

From TOML, StrictDoc borrowed the ``[]`` bracket syntax to create the ``[REQUIREMENT]``, ``[SECTION]`` and other blocks but uses the YAML-like syntax for these blocks' fields, for example:

.. code-block::

    [REQUIREMENT]
    TITLE: Requirement ABC
    STATEMENT: The system A shall do B when C.

**TOML/YAML: Arrays/dictionaries**

StrictDoc has a rudimentary support of arrays and dictionaries. For example, the syntax for defining the document's ``[GRAMMAR]`` resembles what would look like an array of records in YAML:

.. code-block::

    [GRAMMAR]
    ELEMENTS:
    - TAG: REQUIREMENT
      FIELDS:
      - TITLE: UID
        TYPE: String
        REQUIRED: True
      - TITLE: LEVEL
        TYPE: String
        REQUIRED: False

**Capitalization of reserved keywords from ASN.1**

From ASN.1, StrictDoc borrows the idea of having all reserved fields capitalized. This helps to visually distinguish between the grammar content and user content.

**Nested sections**

From HTML, the idea of opening and closing tags is taken to avoid any nesting that would otherwise be required to support the deeply nested documents with up to 6 or 8 levels, e.g., 1.1.1.1.1.1.1...

.. code-block::

    [SECTION]
    TITLE: Section 1

    [SECTION]
    TITLE: Section 1.1

    ...

    [/SECTION]

    [/SECTION]

Taking HTML or XML as-is didn't seem like a good option because of the heavy visual noise that is produced around the actual content by the surrounding tags.

**Multiline strings**

The support of multiline strings is arranged by a custom solution which helps to avoid any nesting of multiline text as well as to visually indicate the start and end parts of the multiline string in a visually unambiguous way. This is how the multiline string is declared:

.. code-block::

    [REQUIREMENT]
    TITLE: Requirement ABC
    STATEMENT: >>>
    The multiline requirement statement
    without any nesting.
    >>>

**Discarded options**

Taking TOML or YAML as-is didn't seem like a good option because these formats are designed to be used for configuration files or data serialization and not for large documents with hundreds of requirements. The most obvious problems for reusing either of TOML or YAML directly would have been with encoding the deeply nested documents and supporting readable and non-nested multiline strings.
<<<

[/SECTION]

[SECTION]
MID: 1d4220cc9a5444a5bdbaee91c8c50670
TITLE: How StrictDoc compares to other tools?

[SECTION]
MID: a4533ae81bfe446295242add9156198e
TITLE: Doorstop

[TEXT]
MID: d0c305180d8747a1b70254eaf2c4f201
STATEMENT: >>>
The StrictDoc project is a close successor of another project called
`Doorstop <https://github.com/doorstop-dev/doorstop>`_.

    Doorstop is a requirements management tool that facilitates the storage of
    textual requirements alongside source code in version control.

The author of Doorstop has published a `paper about Doorstop <http://www.scirp.org/journal/PaperInformation.aspx?PaperID=44268#.UzYtfWRdXEZ>`_
where the rationale behind text-based requirements management is provided.

The first version of StrictDoc had started as a fork of the Doorstop project.
However, after a while, the StrictDoc was started from scratch as a separate
project. At this point, StrictDoc and Doorstop do not share any code but
StrictDoc still shares with Doorstop their common underlying design principles:

- Both Doorstop and StrictDoc are written using Python. Both are pip packages which are easy-to-install.
- Both Doorstop and StrictDoc provide a command-line interface.
- Both Doorstop and StrictDoc use text files for requirements management.
- Both Doorstop and StrictDoc encourage collocation of code and documentation.
  When documentation is hosted close to code it has less chances of diverging
  from the actual implementation or becoming outdated.
- As the free and open source projects, both Doorstop and StrictDoc seem to
  struggle to find resources for development of specialized GUI interfaces this
  is why both tools give a preference to supporting exporting documentation
  pages to HTML format as the primary export feature.

StrictDoc differs from Doorstop in a number of aspects:

- Doorstop stores requirements in YAML files, one separate file per requirement
  (`example <https://github.com/doorstop-dev/doorstop/blob/804153c67c7c5466ee94e9553118cc3df03a56f9/reqs/REQ001.yml>`_).
  The document in Doorstop is assembled from the requirements files into a
  single logical document during the document generation process.
  StrictDoc's documentation unit is one document stored in an .sdoc file. Such a
  document can have multiple requirements grouped by sections.
- In YAML files, Doorstop stores requirements properties such as
  ``normative: true`` or ``level: 2.3`` for which Doorstop provides validations.
  Such a design decision, in fact, assumes an existence of implicitly-defined
  grammar which is encoded "ad-hoc" in the parsing and validation rules of
  Doorstop.
  StrictDoc takes a different approach and defines its grammar explicitly using
  a tool for creating Domain-Specific Languages called `textX <https://github.com/textX/textX>`_.
  TextX support allows StrictDoc to encode a strict type-safe grammar in a
  `single grammar file <https://github.com/strictdoc-project/strictdoc/blob/93486a0e9fb30b141187587eae9e995cd86c6cbf/strictdoc/backend/dsl/grammar.py>`_
  that StrictDoc uses to parse the documentation files
  using the parsing capabilities provided by textX out of the box.

The roadmap of StrictDoc contains a work item for supporting the export/import
to/from Doorstop format.
<<<

[/SECTION]

[SECTION]
MID: 5012af516d18447caa3a2dbce97d3e4a
TITLE: Sphinx

[TEXT]
MID: 74b6be0dc2bb485987d8731348cdf5ce
STATEMENT: >>>
Both Sphinx and StrictDoc are both documentation generators but StrictDoc is at
a higher level of abstraction: StrictDoc's specialization is requirements and
specifications documents. StrictDoc can generate documentation to a number of
formats including HTML format as well as the RST format which is a default
input format for Sphinx. A two stage generation is therefore possible:
StrictDoc generates RST documentation which then can be generated to HTML, PDF,
and other formats using Sphinx.

If you are reading this documentation at
https://strictdoc.readthedocs.io/en/latest
then you are already looking at the example: this documentation stored in
`strictdoc_02_faq <https://github.com/strictdoc-project/strictdoc/blob/main/docs/strictdoc_02_faq.sdoc>`_
is converted to RST format by StrictDoc which is further converted to the HTML
website by readthedocs which uses Sphinx under the hood. The
``StrictDoc -> RST -> Sphinx -> PDF`` example is also generated using readthedocs:
`StrictDoc <https://strictdoc.readthedocs.io/_/downloads/en/latest/pdf/>`_.
<<<

[/SECTION]

[SECTION]
MID: 515bcae39d1f48eda0b72562871ab15a
TITLE: Sphinx-Needs

[TEXT]
MID: 602327a9b8654e1eab4bc265e172a63d
STATEMENT: >>>
`Sphinx-Needs <https://sphinxcontrib-needs.readthedocs.io/en/latest/>`_ is a
text-based requirements management system based on Sphinx. It is implemented
as a Sphinx extension which extends the
`reStructuredText (RST)
<https://docutils.sourceforge.io/docs/user/rst/quickref.html>`_
markup language with an additional syntax for writing requirements documents.

Sphinx-Needs was a great source of inspiration for the second version of
StrictDoc which was first implemented as a Sphinx extension and then as a more
independent library on top of `docutils <https://docutils.sourceforge.io/>`_
that Sphinx uses for the underlying RST syntax processing work.

The similarities between Sphinx-Needs and StrictDoc:

- In contrast to Doorstop, both Sphinx-Needs and StrictDoc do not split a
  document into many small files, one file per single requirement (see
  discussion
  `doorstop#401 <https://github.com/doorstop-dev/doorstop/issues/401>`_). Both
  tools follow the "file per document" approach.
- Sphinx-Needs has a
  `well-developed language
  <https://sphinxcontrib-needs.readthedocs.io/en/latest/directives/index.html>`_
  based on custom RST directives, such
  as ``req::``, ``spec::``, ``needtable::``, etc. The RST document is parsed
  by Sphinx/docutils into RST abstract syntax tree (AST) which allows creating
  an object graph out for the documents and their requirements from the RST
  document. StrictDoc uses textX for building an AST from a SDoc document.
  Essentially, both Sphinx-Needs and StrictDoc work in a similar way but use
  different markup languages and tooling for the job.

The difference between Sphinx-Needs and StrictDoc:

- RST tooling provided by Sphinx/docutils is very powerful, yet it can also be
  rather limiting. The RST syntax and underlying docutils tooling do not allow
  much flexibility needed for creating a language for defining requirements
  using a custom and explicit grammar, a feature that became a cornerstone of
  StrictDoc. This was a major reason why the third generation of
  StrictDoc started with a migration from docutils to
  `textX <https://github.com/textX/textX>`_ which is a
  dedicated tool for creating custom Domain-Specific Languages. After the
  migration to textX, StrictDoc is no longer restricted to the limitations of
  the RST document but it is still possible to generate SDoc files to RST
  using StrictDoc and then further generate RST to HTML/PDF and other formats
  using Sphinx.
- Sphinx-Needs has an impressive list of config options and features that
  StrictDoc is missing. Examples: Customizing the look of the requirements,
  `Roles <https://sphinxcontrib-needs.readthedocs.io/en/latest/roles.html>`_,
  `Services
  <https://sphinxcontrib-needs.readthedocs.io/en/latest/services/index.html>`_
  and
  `others
  <https://sphinxcontrib-needs.readthedocs.io/en/latest/index.html>`_.
<<<

[/SECTION]

[SECTION]
MID: 4a77366154d74cf7ab34044bed1cd542
TITLE: FRET

[TEXT]
MID: e3eb1be604c6499292339ecbe7620c60
STATEMENT: >>>
`FRET <https://github.com/NASA-SW-VnV/fret>`_ is a framework for the
elicitation, specification, formalization and understanding of requirements.

    - Users enter system requirements in a specialized natural language.
    - FRET helps understanding and review of semantics by utilizing a variety of forms
      for each requirement: natural language description, formal mathematical logics,
      and diagrams.
    - Requirements can be defined in a hierarchical fashion and can be exported
      in a variety of forms to be used by analysis tools.

FRET has an impressive list of
`Publications <https://github.com/NASA-SW-VnV/fret/blob/master/PUBLICATIONS.md>`_.

FRET's user interface is built with Electron.
<<<

[/SECTION]

[/SECTION]

[SECTION]
MID: ff143a18e98144bd86e10e29616c187b
TITLE: How long has the StrictDoc project been around?

[TEXT]
MID: 47d60404cf574aebb8c83795589c4137
STATEMENT: >>>
The first StrictDoc commit dates back to ``2019-08-10``. A short development chronology of StrictDoc is as follows:

**2019 – July – August**

StrictDoc is a result of several attempts to find a solution for working with
text-based requirements. The first version of StrictDoc had started as a fork of the Doorstop project. However, after a while, StrictDoc was started from scratch as a separate project.

**2019 – August**

StrictDoc, first generation, the first commit dates to ``2019-08-10``. Markdown-based C++ program. Custom requirements metadata in YAML.

**2020 – January**

StrictDoc, second generation: RST/Sphinx-based Python program. Using Sphinx extensions to manage meta information.

**2020 – May**

The current StrictDoc repository was created on GitHub: the first commit dates back ``2020-05-14``. The code still uses RST for parsing requirements meta information and PySide for GUI.

The result of these efforts was the realization that a text-based requirements and specifications management tool could be built on top of a domain-specific language (DSL) created specifically for the purpose of writing requirements and specifications documents. Such a language allows explicit definition of a document data model which is called "grammar".

**2020 – July**

The custom RST parser was replaced with a TextX-based DSL. Since then, StrictDoc has been using TextX for parsing SDoc files.

**2022 – November**

The FastAPI/Turbo/Stimulus-based Web interface prototype was created to complement the text-based interface with a graphical user interface (GUI). When the Web-based GUI is stable, StrictDoc may become useable by non-programmers too.

See also: [LINK: SECTION-DP-Project-milestones].
<<<

[/SECTION]

[SECTION]
MID: 6e5ed6bb36634220a0c583d21c96295f
TITLE: Which StrictDoc statistics are available?

[TEXT]
MID: 730bfedff6b24c34a6d6331051fd76d3
STATEMENT: >>>
Most relevant GitHub statistics:

- `Contributors <https://github.com/strictdoc-project/strictdoc/graphs/contributors>`_

The `pip trends <https://piptrends.com>`_ helps to visualize the Pip package download stats. The ``reqif`` satellite project is included for comparison as well:
`strictdoc vs reqif <https://piptrends.com/compare/strictdoc-vs-reqif>`_.
<<<

[/SECTION]
