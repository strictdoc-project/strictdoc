[DOCUMENT]
TITLE: Hello world doc

[REQUIREMENT]
UID: REQ-1
TITLE: Requirement #1
STATEMENT: System shall do 1.
COMMENT: This is a comment 1111.
COMMENT: This is a comment 111.
COMMENT: This is a comment 11.
COMMENT: This is a comment #2.
