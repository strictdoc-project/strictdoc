[DOCUMENT]
TITLE: Test document

[REQUIREMENT]
UID: REQ-1
TITLE: Requirement 1
STATEMENT: The system shall provide requirement 1.

[REQUIREMENT]
UID: REQ-2
TITLE: Requirement 2
STATEMENT: The system shall provide requirement 2.

[REQUIREMENT]
UID: REQ-3
TITLE: Requirement 3
STATEMENT: The system shall provide requirement 3.

[REQUIREMENT]
UID: REQ-4
TITLE: Requirement 4
STATEMENT: The system shall provide requirement 4.

[REQUIREMENT]
UID: REQ-5
TITLE: Requirement 5
STATEMENT: The system shall provide requirement 5.

[REQUIREMENT]
UID: REQ-6
TITLE: Requirement 6
STATEMENT: The system shall provide requirement 6.
