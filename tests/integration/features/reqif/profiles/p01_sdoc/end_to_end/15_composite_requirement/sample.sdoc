[DOCUMENT]
TITLE: sample

[GRAMMAR]
ELEMENTS:
- TAG: COMPOSITE_REQUIREMENT
  PROPERTIES:
    IS_COMPOSITE: True
  FIELDS:
  - TITLE: UID
    TYPE: String
    REQUIRED: False
  - TITLE: STATEMENT
    TYPE: String
    REQUIRED: False
- TAG: REQUIREMENT
  FIELDS:
  - TITLE: STATEMENT
    TYPE: String
    REQUIRED: False

[[COMPOSITE_REQUIREMENT]]
UID: REQ-1.1.1
STATEMENT: >>>
The mapping function shall map requirement_ID to UID.
<<<

[REQUIREMENT]
STATEMENT: >>>
Shall statement.
<<<

[[/COMPOSITE_REQUIREMENT]]
