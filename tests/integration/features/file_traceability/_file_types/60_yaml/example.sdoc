[DOCUMENT]
TITLE: Example: Traceability between requirements and source files

[REQUIREMENT]
UID: REQ-001
TITLE: Whole file reference
STATEMENT: This requirement references the whole file.
RELATIONS:
- TYPE: File
  VALUE: file.yaml

[REQUIREMENT]
UID: REQ-002
TITLE: Source range reference
STATEMENT: This requirement references a range in the file.
RELATIONS:
- TYPE: File
  VALUE: file.yaml

[REQUIREMENT]
UID: REQ-003
TITLE: Source range reference
STATEMENT: This requirement references a range in the file.
RELATIONS:
- TYPE: File
  VALUE: file.yaml
