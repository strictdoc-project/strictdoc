[DOCUMENT]
TITLE: Hello world doc

[REQUIREMENT]
TITLE: Req-1
STATEMENT: ...

[REQUIREMENT]
TITLE: Req-2
STATEMENT: ...

[REQUIREMENT]
TITLE: Req-3
STATEMENT: ...

[REQUIREMENT]
TITLE: Req-4
STATEMENT: ...
