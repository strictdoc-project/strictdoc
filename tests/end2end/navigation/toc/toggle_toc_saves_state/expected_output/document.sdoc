[DOCUMENT]
TITLE: Document title

[TEXT]
STATEMENT: >>>
Hello world!
<<<

[[SECTION]]
TITLE: Section title

[TEXT]
STATEMENT: >>>
This is a free text of this section.
<<<

[[/SECTION]]

[REQUIREMENT]
TITLE: Requirement 1 title
STATEMENT: >>>
Requirement statement.
<<<

[REQUIREMENT]
TITLE: Requirement 2 title
STATEMENT: >>>
Requirement statement.
<<<
