[DOCUMENT]
TITLE: Hello world doc

[REQUIREMENT]
UID: REQ-001
TITLE: High-level requirement title #1
STATEMENT: High-level requirement statement #1.

[REQUIREMENT]
UID: REQ-002
TITLE: High-level requirement title #2
STATEMENT: High-level requirement statement #2.

[REQUIREMENT]
UID: REQ-003
TITLE: High-level requirement title #3
STATEMENT: High-level requirement statement #3.
