[DOCUMENT]
TITLE: Hello world doc

[COMPOSITE_REQUIREMENT]
STATEMENT: System shall do 1.

[REQUIREMENT]
STATEMENT: System shall do 1.

[/COMPOSITE_REQUIREMENT]

[COMPOSITE_REQUIREMENT]
STATEMENT: System shall do 2.

[REQUIREMENT]
STATEMENT: System shall do 2.

[/COMPOSITE_REQUIREMENT]

[COMPOSITE_REQUIREMENT]
STATEMENT: System shall do 3.

[REQUIREMENT]
STATEMENT: System shall do 3.

[/COMPOSITE_REQUIREMENT]
