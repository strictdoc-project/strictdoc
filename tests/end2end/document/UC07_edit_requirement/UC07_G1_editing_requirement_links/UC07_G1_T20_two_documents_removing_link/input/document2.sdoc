[DOCUMENT]
TITLE: Document 2

[FREETEXT]
Hello world 2!
[/FREETEXT]

[REQUIREMENT]
UID: REQ-002
REFS:
- TYPE: Parent
  VALUE: REQ-001
TITLE: Requirement title #2
STATEMENT: >>>
Requirement statement #2.
<<<
