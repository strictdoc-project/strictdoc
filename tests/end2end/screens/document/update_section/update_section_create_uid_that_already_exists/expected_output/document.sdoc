[DOCUMENT]
TITLE: Document 1

[FREETEXT]
Hello world!
[/FREETEXT]

[SECTION]
TITLE: First section

[FREETEXT]
This is a free text of this section.
[/FREETEXT]

[/SECTION]

[SECTION]
UID: Existing-Section-UID
TITLE: Second section

[FREETEXT]
This is a free text of this section.
[/FREETEXT]

[/SECTION]
