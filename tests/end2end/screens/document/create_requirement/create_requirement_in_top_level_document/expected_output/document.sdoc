[DOCUMENT]
TITLE: Document 1

[REQUIREMENT]
UID: REQ-001
TITLE: Requirement title #1
STATEMENT: >>>
Requirement statement #1.
<<<
RATIONALE: >>>
Requirement rationale #1.
<<<

[REQUIREMENT]
UID: REQ-002
TITLE: Requirement title #2
STATEMENT: >>>
Requirement statement #2.
<<<
RATIONALE: >>>
Requirement rationale #2.
<<<

[REQUIREMENT]
UID: REQ-003
TITLE: Requirement title #3
STATEMENT: >>>
Requirement statement #3.
<<<
RATIONALE: >>>
Requirement rationale #3.
<<<
