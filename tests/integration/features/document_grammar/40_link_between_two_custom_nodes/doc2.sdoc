[DOCUMENT]
TITLE: Test document #2

[GRAMMAR]
ELEMENTS:
- TAG: OBJECTIVE
  FIELDS:
  - TITLE: UID
    TYPE: String
    REQUIRED: False
  - TITLE: TITLE
    TYPE: String
    REQUIRED: False
  - TITLE: STATEMENT
    TYPE: String
    REQUIRED: False

[OBJECTIVE]
UID: OBJ-1
TITLE: Objective #1
STATEMENT: Objective #1 statement.
