[DOCUMENT]
TITLE: Document

[GRAMMAR]
ELEMENTS:
- TAG: REQUIREMENT
  FIELDS:
  - TITLE: UID
    TYPE: String
    REQUIRED: False
  - TITLE: STATEMENT
    TYPE: String
    REQUIRED: False
  RELATIONS:
  - TYPE: File

[REQUIREMENT]
UID: REQ-RANGE
STATEMENT: Linked to a short line range and to a long function.
RELATIONS:
- TYPE: File
  VALUE: src/example.py
  LINE_RANGE: 1, 2
- TYPE: File
  VALUE: src/example.py
  FUNCTION: long_function

[REQUIREMENT]
UID: REQ-BACKWARD
STATEMENT: Linked from the source file.
