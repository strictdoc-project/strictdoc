# ...Anonymized-7259913054...

# Specification: sample

## ...Anonymized-1567910156...: ...Anonymized-8302745742... (Heading)

### ...Anonymized-7584165793...: ...Anonymized-9054024535... (Heading)

### ...Anonymized-1859327298...: ...Anonymized-9129086814... (Heading)

### ...Anonymized-4628192831...: ...Anonymized-6947442502... (Heading)

#### ...Anonymized-1300250218...: ...Anonymized-8866683558... (Document)

### ...Anonymized-5528737094...: ...Anonymized-3235655901... (Heading)

## ...Anonymized-3476924022...: ...Anonymized-6292460274... (Heading)

### ...Anonymized-405712407...: ...Anonymized-9881735258... (Heading)

#### ...Anonymized-1443606887...: ...Anonymized-552150625... (Heading)

#### ...Anonymized-4344877209...: ...Anonymized-220781768... (Heading)

#### ...Anonymized-6218470561...: ...Anonymized-8189832167... (Heading)

#### ...Anonymized-3977207881...: ...Anonymized-2203395830... (Heading)

#### ...Anonymized-2644691225...: ...Anonymized-3849168842... (Heading)

#### ...Anonymized-1982965503...: ...Anonymized-5915886979... (Heading)

## ...Anonymized-2941169342...: ...Anonymized-9743096900... (Heading)

## ...Anonymized-2232655710...: ...Anonymized-3302641316... (Heading)

## ...Anonymized-4760351589...: ...Anonymized-848542830... (Heading)

## ...Anonymized-3801107121...: ...Anonymized-511784953... (Heading)

### ...Anonymized-4343463957...: ...Anonymized-2728706743... (Heading)

#### ...Anonymized-1890729041...: ...Anonymized-8651603154... (DCPRS)
...Anonymized-2087513185...

### ...Anonymized-4628638013...: ...Anonymized-9841011696... (Heading)

#### ...Anonymized-422678150...: ...Anonymized-1297577872... (DCPRS)
...Anonymized-1828513934...

#### ...Anonymized-3823459017...: ...Anonymized-6268519580... (Heading)

##### ...Anonymized-9325576769...: ...Anonymized-1914870727... (DCPRS)
...Anonymized-7741683588...

##### ...Anonymized-2713160172...: ...Anonymized-4315511969... (Heading)

#### ...Anonymized-6644157878...: ...Anonymized-7060489806... (Heading)

##### ...Anonymized-744921517...: ...Anonymized-2235455538... (DCPRS)
...Anonymized-8325796898...

##### ...Anonymized-929117292...: ...Anonymized-4543847982... (Heading)

#### ...Anonymized-65684735...: ...Anonymized-5696176087... (Heading)

##### ...Anonymized-220285971...: ...Anonymized-3165240195... (DCPRS)
...Anonymized-8205109053...

### ...Anonymized-4546224745...: ...Anonymized-2107033738... (Heading)

## ...Anonymized-8549067849...: ...Anonymized-1885330867... (Heading)

### ...Anonymized-5460224227...: ...Anonymized-3347139137... (Heading)

### ...Anonymized-7770394381...: ...Anonymized-9609746885... (Heading)

#### ...Anonymized-3581321690...: ...Anonymized-4994486814... (DCPRS)
...Anonymized-141441514...

#### ...Anonymized-552311841...: ...Anonymized-3814499988... (DCPRS)
...Anonymized-9711080681...

#### ...Anonymized-236348242...: ...Anonymized-8271467979... (DCPRS)
...Anonymized-7688808623...

#### ...Anonymized-4517678322...: ...Anonymized-6322076937... (DCPRS)
...Anonymized-7776501858...

#### ...Anonymized-3779057531...: ...Anonymized-7971195117... (DCPRS)
...Anonymized-2626514360...

#### ...Anonymized-1199224361...: ...Anonymized-2365556077... (DCPRS)
...Anonymized-5020016015...

#### ...Anonymized-1447716607...: ...Anonymized-9094628254... (DCPRS)
...Anonymized-8423889971...

#### ...Anonymized-9528977567...: ...Anonymized-1904308738... (Heading)

##### ...Anonymized-9287248007...: ...Anonymized-3330761254... (DCPRS)
...Anonymized-9368492491...

##### ...Anonymized-8497383730...: ...Anonymized-8967398978... (DCPRS)
...Anonymized-7183025451...

##### ...Anonymized-439184680...: ...Anonymized-9714961743... (DCPRS)
...Anonymized-459724116...

##### ...Anonymized-5303132855...: ...Anonymized-9716189333... (DCPRS)
...Anonymized-6636827005...

##### ...Anonymized-7169546310...: ...Anonymized-9682246591... (DCPRS)
...Anonymized-8185106799...

##### ...Anonymized-4047040496...: ...Anonymized-8392486239... (DCPRS)
...Anonymized-2770874074...

##### ...Anonymized-7602209795...: ...Anonymized-5918909784... (DCPRS)
...Anonymized-2503026613...

##### ...Anonymized-497191972...: ...Anonymized-8998705652... (DCPRS)
...Anonymized-8905014884...

##### ...Anonymized-3849828860...: ...Anonymized-9199422890... (DCPRS)
...Anonymized-3337713458...

##### ...Anonymized-5377541413...: ...Anonymized-3495068021... (DCPRS)
...Anonymized-1256556035...

##### ...Anonymized-5040640418...: ...Anonymized-8452623958... (DCPRS)
...Anonymized-654150806...

##### ...Anonymized-5254463344...: ...Anonymized-3648321526... (DCPRS)
...Anonymized-8415773905...

#### ...Anonymized-9694617440...: ...Anonymized-6522749027... (Heading)

##### ...Anonymized-6218650018...: ...Anonymized-5116575856... (DCPRS)
...Anonymized-3418466860...

##### ...Anonymized-884094677...: ...Anonymized-3471034546... (DCPRS)
...Anonymized-949818211...

##### ...Anonymized-8356771282...: ...Anonymized-554727204... (DCPRS)
...Anonymized-9248083159...

##### ...Anonymized-2525261970...: ...Anonymized-4500050551... (DCPRS)
...Anonymized-4560993492...

##### ...Anonymized-3361230985...: ...Anonymized-9986318994... (DCPRS)
...Anonymized-9066536825...

##### ...Anonymized-8738435202...: ...Anonymized-511780480... (DCPRS)
...Anonymized-6164201809...

#### ...Anonymized-9405074238...: ...Anonymized-462315954... (Heading)

##### ...Anonymized-2637732234...: ...Anonymized-8062014459... (DCPRS)
...Anonymized-6911156538...

##### ...Anonymized-6877290819...: ...Anonymized-6525087259... (DCPRS)
...Anonymized-1683251619...

##### ...Anonymized-9436575982...: ...Anonymized-1424360090... (DCPRS)
...Anonymized-7713260133...

##### ...Anonymized-8108608228...: ...Anonymized-2513865100... (DCPRS)
...Anonymized-2699246835...

##### ...Anonymized-7136724629...: ...Anonymized-263821908... (DCPRS)
...Anonymized-5189095323...

##### ...Anonymized-6227419140...: ...Anonymized-5927915516... (DCPRS)
...Anonymized-2935552249...

##### ...Anonymized-7951666085...: ...Anonymized-8178088268... (DCPRS)
...Anonymized-7513309484...

#### ...Anonymized-6238043288...: ...Anonymized-3944072270... (Heading)

##### ...Anonymized-4182165825...: ...Anonymized-5684444556... (DCPRS)
...Anonymized-6366575243...

##### ...Anonymized-1135423924...: ...Anonymized-9812936584... (DCPRS)
...Anonymized-3589199435...

##### ...Anonymized-9556525472...: ...Anonymized-8219958399... (DCPRS)
...Anonymized-6484288007...

##### ...Anonymized-5853001651...: ...Anonymized-3628161945... (Heading)

###### ...Anonymized-3208414997...: ...Anonymized-6976668288... (DCPRS)
...Anonymized-9205927058...

###### ...Anonymized-7078675370...: ...Anonymized-7324178850... (DCPRS)
...Anonymized-6130221674...

###### ...Anonymized-8748282090...: ...Anonymized-777449241... (DCPRS)
...Anonymized-6104319096...

### ...Anonymized-7711894702...: ...Anonymized-2525064... (Heading)

#### ...Anonymized-4856971097...: ...Anonymized-4351127241... (DCPRS)
...Anonymized-5700797132...

#### ...Anonymized-255257247...: ...Anonymized-2478294741... (DCPRS)
...Anonymized-4790295697...

#### ...Anonymized-4271704871...: ...Anonymized-8336809210... (DCPRS)
...Anonymized-5109898138...

#### ...Anonymized-4256058190...: ...Anonymized-3394986330... (DCPRS)
...Anonymized-4710584848...

#### ...Anonymized-2344472385...: ...Anonymized-2926314372... (DCPRS)
...Anonymized-166869359...

#### ...Anonymized-1574008872...: ...Anonymized-357025202... (DCPRS)
...Anonymized-1855929405...

#### ...Anonymized-5329380310...: ...Anonymized-1447827518... (DCPRS)
...Anonymized-3381681264...

#### ...Anonymized-5977721359...: ...Anonymized-2691231999... (DCPRS)
...Anonymized-6747899467...

### ...Anonymized-8620509769...: ...Anonymized-4740092073... (Heading)

#### ...Anonymized-2284932371...: ...Anonymized-7804677192... (DCPRS)
...Anonymized-1639739024...

#### ...Anonymized-1341522708...: ...Anonymized-9075303301... (DCPRS)
...Anonymized-1512107600...

#### ...Anonymized-4115634577...: ...Anonymized-4637835705... (DCPRS)
...Anonymized-2661813959...

#### ...Anonymized-9601727033...: ...Anonymized-9857510153... (DCPRS)
...Anonymized-5053122332...

#### ...Anonymized-3715633700...: ...Anonymized-2691231999... (DCPRS)
...Anonymized-6747899467...

### ...Anonymized-7809462939...: ...Anonymized-5100920... (Heading)

### ...Anonymized-7638090669...: ...Anonymized-9364436384... (Heading)

### ...Anonymized-5712596071...: ...Anonymized-576683829... (Heading)

#### ...Anonymized-2776068889...: ...Anonymized-1517221830... (DCPRS)
...Anonymized-3677729572...

## ...Anonymized-8653786480...: ...Anonymized-3853402103... (Heading)

## ...Anonymized-9599308248...: ...Anonymized-1200856893... (Heading)

### ...Anonymized-887082839...: ...Anonymized-2691231999... (DCPRS)
...Anonymized-6747899467...

## ...Anonymized-8052426480...: ...Anonymized-9585318457... (Heading)

## ...Anonymized-764089332...: ...Anonymized-9289393786... (Heading)
