[DOCUMENT]
TITLE: ewwer

[REQUIREMENT]
STATEMENT: >>>
sdfsdf
<<<

[SECTION]
TITLE: ssssss

[REQUIREMENT]
STATEMENT: >>>
rtnrtbrtnrtn
<<<

[/SECTION]

[REQUIREMENT]
STATEMENT: >>>
yyuyukuykuykuykyukuy
<<<
