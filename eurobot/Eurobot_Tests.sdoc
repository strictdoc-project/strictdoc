[DOCUMENT]
TITLE: Системные испытания

[GRAMMAR]
IMPORT_FROM_FILE: @eurobot_tests

[TEXT]
STATEMENT: >>>
Испытания, выполняемые вручную. Поле ``STATUS`` фиксирует текущий результат;
команда обновляет его вручную после каждой сессии испытаний и указывает
``Not Executed`` для нового тестового случая. У ``REQ-4`` намеренно нет
тестового случая, чтобы Матрица трассируемости показывала, как выглядит
непроверенное требование.
<<<

[[SECTION]]
TITLE: Готовность модулей

[[SECTION]]
TITLE: Механики

[[/SECTION]]

[[SECTION]]
TITLE: Электроники

[[/SECTION]]

[[SECTION]]
TITLE: Программного обеспечения

[[/SECTION]]

[[/SECTION]]

[[SECTION]]
TITLE: Системные испытания

[[SECTION]]
TITLE: Допуск к соревнованиям

[TEST_CASE]
UID: REQ-7
TITLE: Динамическая проверка 1 - старт
STATUS: Not Executed
STATEMENT: >>>
1. Установить робота на старт (dbg.pose.position.x=0 И dbg.pose.position.y=0)

2. Выдернуть стартовый корд (input.started_cord=true)

ЕСЛИ робот выехал из зоны старта (dbg.pose.position.x > 0.125 И dbg.pose.position.y > 0.125)

ТО УСПЕХ
ИНАЧЕ ПРОВАЛ
<<<
RELATIONS:
- TYPE: Parent
  VALUE: REQ-6
  ROLE: VERIFIES

[[/SECTION]]

[[/SECTION]]

[TEST_CASE]
UID: TC-1
TITLE: Измерение периметра при старте
STATUS: Passed
STATEMENT: >>>
Поставьте робота на стол в стартовой конфигурации и оберните измерительную
ленту вокруг его периметра. Зафиксируйте значение периметра.

Ожидаемый результат: периметр не более 1200 мм.
<<<
RELATIONS:
- TYPE: Parent
  VALUE: REQ-1
  ROLE: VERIFIES

[TEST_CASE]
UID: TC-2
TITLE: Измерение высоты
STATUS: Not Executed
STATEMENT: >>>
Снимите мачту крепления маяка. Измерьте расстояние от поверхности стола до
самой высокой точки робота.

Ожидаемый результат: высота не более 350 мм.
<<<
RELATIONS:
- TYPE: Parent
  VALUE: REQ-2
  ROLE: VERIFIES

[TEST_CASE]
UID: TC-3
TITLE: Аварийная остановка под нагрузкой
STATUS: Failed
STATEMENT: >>>
Разгоните робота на полной скорости вперёд и нажмите кнопку аварийной
остановки. Понаблюдайте за двигателями и приводами.

Ожидаемый результат: всё движение прекращается, ни один привод не
удерживает питание, и робот остаётся обесточенным до отпускания кнопки.
<<<
RELATIONS:
- TYPE: Parent
  VALUE: REQ-3
  ROLE: VERIFIES
