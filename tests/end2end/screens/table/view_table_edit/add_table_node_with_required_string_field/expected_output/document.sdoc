[DOCUMENT]
TITLE: Document

[GRAMMAR]
ELEMENTS:
- TAG: TEXT
  FIELDS:
  - TITLE: UID
    TYPE: String
    REQUIRED: False
  - TITLE: STATEMENT
    TYPE: String
    REQUIRED: True
- TAG: TASK
  FIELDS:
  - TITLE: UID
    TYPE: String
    REQUIRED: False
  - TITLE: PRIORITY
    TYPE: String
    REQUIRED: True
  - TITLE: TITLE
    TYPE: String
    REQUIRED: False

[TASK]
UID: REQ-1
PRIORITY: TBD

[TASK]
UID: TASK-1
PRIORITY: High
TITLE: Existing task
