[DOCUMENT]
TITLE: Hello world doc

[GRAMMAR]
ELEMENTS:
- TAG: REQUIREMENT
  FIELDS:
  - TITLE: UID
    TYPE: String
    REQUIRED: True
  - TITLE: TITLE
    TYPE: String
    REQUIRED: True
  - TITLE: STATEMENT
    TYPE: String
    REQUIRED: True
  - TITLE: COMMENT
    TYPE: String
    REQUIRED: False
  - TITLE: OWNER
    TYPE: String
    REQUIRED: False
  - TITLE: PRIORITY
    TYPE: SingleChoice(LOW, MEDIUM, HIGH)
    REQUIRED: True
  RELATIONS:
  - TYPE: Parent
  - TYPE: File

[REQUIREMENT]
UID: REQ-001
TITLE: Title #1
STATEMENT: Statement #1
COMMENT: Simple Comment
OWNER: Owner #1
PRIORITY: HIGH

[REQUIREMENT]
UID: REQ-002
TITLE: Title #2
STATEMENT: Statement #2
COMMENT: >>>
Multiline Comment: line 1
Multiline Comment: line 2
Multiline Comment: line 3
<<<
OWNER: Owner #2
PRIORITY: MEDIUM
RELATIONS:
- TYPE: Parent
  VALUE: REQ-001

[REQUIREMENT]
UID: REQ-003
TITLE: Title #3
STATEMENT: Statement #3
COMMENT: Simple Comment #1
COMMENT: >>>
Multiline Comment #2: line 1
Multiline Comment #2: line 2
Multiline Comment #2: line 3
<<<
COMMENT: >>>
Multiline Comment #3: line 1
Multiline Comment #3: line 2
Multiline Comment #3: line 3
<<<
COMMENT: Simple Comment #4
PRIORITY: LOW
RELATIONS:
- TYPE: Parent
  VALUE: REQ-002

[REQUIREMENT]
UID: REQ-004
TITLE: Title #4
STATEMENT: Statement #4
PRIORITY: LOW
RELATIONS:
- TYPE: Parent
  VALUE: REQ-002
- TYPE: File
  VALUE: src/samplefile.cpp
