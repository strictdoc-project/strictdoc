[DOCUMENT]
TITLE: Dummy Software Requirements Specification #3
OPTIONS:
  ENABLE_MID: True

[GRAMMAR]
ELEMENTS:
- TAG: TEXT
  FIELDS:
  - TITLE: MID
    TYPE: String
    REQUIRED: False
  - TITLE: UID
    TYPE: String
    REQUIRED: False
  - TITLE: STATEMENT
    TYPE: String
    REQUIRED: True
- TAG: REQUIREMENT
  FIELDS:
  - TITLE: MID
    TYPE: String
    REQUIRED: False
  - TITLE: UID
    TYPE: String
    REQUIRED: False
  - TITLE: TITLE
    TYPE: String
    REQUIRED: False
  - TITLE: STATEMENT
    TYPE: String
    REQUIRED: False
  RELATIONS:
  - TYPE: Parent
  - TYPE: File

[REQUIREMENT]
TITLE: Dummy high-level requirement #1
STATEMENT: System ABC shall do 1.
RELATIONS:
- TYPE: File
  VALUE: file.py

[REQUIREMENT]
TITLE: Dummy high-level requirement #2
STATEMENT: System ABC shall do 2.
RELATIONS:
- TYPE: File
  VALUE: file.py

[REQUIREMENT]
TITLE: Dummy high-level requirement #3
STATEMENT: System ABC shall do 3.
RELATIONS:
- TYPE: File
  VALUE: file.py
