[DOCUMENT]
TITLE: Document 1

[REQUIREMENT]
UID: REQ-001
TITLE: Requirement to delete
STATEMENT: >>>
Delete this requirement.
<<<

[REQUIREMENT]
UID: REQ-002
TITLE: Requirement to keep
STATEMENT: >>>
Keep this requirement.
<<<
