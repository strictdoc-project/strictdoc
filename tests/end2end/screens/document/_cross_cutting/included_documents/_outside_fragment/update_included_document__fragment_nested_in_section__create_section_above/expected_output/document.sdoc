[DOCUMENT]
TITLE: Document 1

[TEXT]
STATEMENT: >>>
Hello world!
<<<

[[SECTION]]
TITLE: Section that nests a document fragment.

[[SECTION]]
TITLE: First section

[[/SECTION]]

[DOCUMENT_FROM_FILE]
FILE: fragment.sdoc

[[/SECTION]]
