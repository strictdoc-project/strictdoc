[DOCUMENT]
TITLE: Document with an RST table

[REQUIREMENT]
STATEMENT: >>>
.. list-table:: Table Example
    :widths: 25 25 50
    :header-rows: 1

    * - Heading row 1, column 1
      - Heading row 1, column 2
      - Heading row 1, column 3
    * - Row 1, column 1
      -
      - Row 1, column 3
    * - Row 2, column 1
      - Row 2, column 2
      - Row 2, column 3
<<<
