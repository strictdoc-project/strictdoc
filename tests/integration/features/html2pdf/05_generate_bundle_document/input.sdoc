[DOCUMENT]
TITLE: Dummy Software Requirements Specification #1
VERSION: @GIT_VERSION, @GIT_BRANCH
DATE: @GIT_COMMIT_DATETIME

[[SECTION]]
UID: SEC-1
TITLE: Section #1

[TEXT]
STATEMENT: >>>
.. image:: _assets/file.svg
   :alt: Test image
   :class: image
   :width: 100%
<<<

[[/SECTION]]
