[DOCUMENT]
TITLE: Hello world doc 2
OPTIONS:
  AUTO_LEVELS: On

[GRAMMAR]
ELEMENTS:
- TAG: SECTION
  PROPERTIES:
    IS_COMPOSITE: True
    PREFIX: None
  FIELDS:
  - TITLE: MID
    TYPE: String
    REQUIRED: False
  - TITLE: UID
    TYPE: String
    REQUIRED: False
  - TITLE: PREFIX
    TYPE: String
    REQUIRED: False
  - TITLE: TITLE
    TYPE: String
    REQUIRED: False
- TAG: REQUIREMENT
  FIELDS:
  - TITLE: MID
    TYPE: String
    REQUIRED: False
  - TITLE: UID
    TYPE: String
    REQUIRED: False
  - TITLE: STATUS
    TYPE: String
    REQUIRED: False
  - TITLE: TITLE
    TYPE: String
    REQUIRED: True
  - TITLE: STATEMENT
    TYPE: String
    REQUIRED: False
- TAG: COMPOSITE_REQUIREMENT
  PROPERTIES:
    IS_COMPOSITE: True
  FIELDS:
  - TITLE: MID
    TYPE: String
    REQUIRED: False
  - TITLE: UID
    TYPE: String
    REQUIRED: False
  - TITLE: TITLE
    TYPE: String
    REQUIRED: False
  - TITLE: STATEMENT
    TYPE: String
    REQUIRED: False

[DOCUMENT_FROM_FILE]
FILE: subnested.sdoc

[[SECTION]]
TITLE: Nested Doc Section

[[COMPOSITE_REQUIREMENT]]
TITLE: Nested Doc Section Composite requirement
STATEMENT: ...

[REQUIREMENT]
TITLE: Nested Doc Section Requirement
STATEMENT: ...

[[/COMPOSITE_REQUIREMENT]]

[[/SECTION]]
