[DOCUMENT]
TITLE: Hello world doc 3
OPTIONS:
  AUTO_LEVELS: On

[TEXT]
STATEMENT: >>>
.. image:: _assets/file.svg
   :alt: Test image
   :class: image
   :width: 100%
<<<

[SECTION]
TITLE: Section 1.2.3

[COMPOSITE_REQUIREMENT]
TITLE: Composite requirement 4.5.6

[REQUIREMENT]
TITLE: Requirement 7.8.9

[/COMPOSITE_REQUIREMENT]

[/SECTION]
