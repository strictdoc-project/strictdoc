[DOCUMENT]
TITLE: Test Document
OPTIONS:
  REQUIREMENT_STYLE: Inline
  DEFAULT_VIEW: PRINT_VIEW
VIEWS:
- ID: BOGUS_VIEW
  NAME: Bogus view
  TAGS:
  - OBJECT_TYPE: BOGUS_OBJECT
    VISIBLE_FIELDS:
    - NAME: UID
      PLACEMENT: XYZ
    - NAME: STATEMENT
    - NAME: RATIONALE
  - OBJECT_TYPE: ASSUMPTION
    VISIBLE_FIELDS:
    - NAME: UID
      PLACEMENT: XYZ
    - NAME: STATEMENT
