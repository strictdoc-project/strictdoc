[DOCUMENT]
TITLE: Test document

[GRAMMAR]
ELEMENTS:
- TAG: REQUIREMENT
  FIELDS:
  - TITLE: ONE
    TYPE: String
    REQUIRED: True
  - TITLE: TWO
    TYPE: String
    REQUIRED: True
  - TITLE: STATEMENT
    TYPE: String
    REQUIRED: False

[REQUIREMENT]
ONE: One-value
TWO: Two-value
ONE: One-value
