[DOCUMENT]
TITLE: Hello world doc

[SECTION]
UID: CHAPTER_1
TITLE: Chapter 1

[FREETEXT]
See [LINK: REQ-1] for more details.
[/FREETEXT]

[TEXT]
UID: THING
STATEMENT: >>>
See [LINK: REQ-2] for more details.
<<<

[REQUIREMENT]
UID: REQ-1
STATEMENT: The foo must bar.
COMMENT: >>>
As the [LINK: THING]y explains.
<<<

[REQUIREMENT]
UID: REQ-2
TITLE: Foo Bar
STATEMENT: >>>
Go and read [LINK: CHAPTER_1].
<<<

[/SECTION]
