# DEMO/NEEDS

# Specification: NEEDS
- ReqIF.Description: ReqView User Needs

## NEEDS-45
© Copyright by Eccam s.r.o. All rights reserved.
- Type: Information

## NEEDS-2: Introduction
- Type: Section

### NEEDS-64: Purpose
- Type: Section

#### NEEDS-67
The main purpose of this document is to provide new ReqView users a working example of a document describing high-level user needs by means of user stories.
- Type: Information

### NEEDS-65: Scope
- Type: Section

#### NEEDS-75
This document specifies top level user needs for a simple HW/SW requirements management tool.
Note: The document is not complete.
- Type: Information

#### NEEDS-66
Users should be able to:
- Capture requirements specifications
- Manage requirements using custom attributes
- Set up requirements traceability
- Browse the requirements traceability matrix (RTM)
- Control project changes
- Filter and search requirements
- Import requirements from MS Word or Excel
- Export requirements to DOCX, XLSX, PDF, HTML, or CSV
- Analyze requirements coverage and impact of changes
- Print requirements specifications
- Integrate ReqView with Jira project management tool
- Integrate ReqView with Enterprise Architect modelling tool
- Type: Information

### NEEDS-1: User Roles
- Type: Section

#### NEEDS-5: Requirements Architect
Requirements Architect defines requirements model and configure the requirements project for other users.
Requirements Architect is typically a QA manager or project manager.
- As a(n): Architect
- I want to:
  - Define custom attributes
  - Configure project traceability
  - Create document templates
- Type: Information

#### NEEDS-6: Editor
Editor defines project requirements and creates requirements and tests documents.
Editor is typically a requirements engineer, business analyst, project manager, QA engineer or a tester.
- I want to:
  - Capture structured requirements
  - Update requirements custom attributes
  - Discuss requirements
  - Maintain requirements traceability links
  - Print requirements
  - Import requirements
  - Export requirements
  - Create traceability reports
- Type: Information

#### NEEDS-7: Reviewer
Reviewer reads project documents, performs review and provides feedback for improving the content of the document.
Reviewer is typically an internal QA expert reviewing requirements and tests, customer or supplier commenting requirements and setting the requirement acceptance state.
- I want to:
  - Provide feedback to requirements specifications
  - Update requirements review status
  - Print requirements
- Type: Information

## NEEDS-3: User Stories
- Type: Section

### NEEDS-9: Requirements Storage
- Type: Epic

#### NEEDS-58: Document Files
- As a(n): Editor
- Acceptance Criteria: Tool supports:
  - saving project in a file
  - opening project from a file
- I want to: save document in a file
- So that: users can open the document for further editing or review
- Status: Implemented
- Type: User Story

#### NEEDS-14: Document Templates
- As a(n): Architect
- Acceptance Criteria: Tool supports:
  - saving a document as a document template file,
  - add a new document into a project from a saved document template file while preserving document attributes definition, values of object attributes and object attachments.
- I want to: save a document as a template file
- So that: I can reuse the document structure and configuration of custom attributes for new documents
- Status: Implemented
- Type: User Story

#### NEEDS-33: Autosave
- As a(n): Editor
- Acceptance Criteria: Tool:
  - instantly saves all the changes,
  - restores the same project content when it is restarted.
- I want to: automatically persist my changes
- So that: I do not lose my changes if the tool is unexpectedly terminated before saving into a file
- Status: Implemented
- Type: User Story

### NEEDS-8: Define Requirements
- Type: Epic

#### NEEDS-68: Requirement Description
- As a(n): Editor
- Acceptance Criteria: Tool supports:
  - setting a description of a selected requirement
  - removing description of a selected requirement
- I want to: specify requirements by a textual description
- So that: the requirements can be reviewed by other users.
- Status: Implemented
- Type: User Story

#### NEEDS-32: Unique IDs
- As a(n): Editor
- Acceptance Criteria: Tool supports:
  - automatic generation of document ID which can not be further changed
- I want to: identify requirements by their unique ID
- So that: I can reference requirements from other documents or communication
- Status: Implemented
- Type: User Story

#### NEEDS-12: Document Structure
- As a(n): Editor
- Acceptance Criteria: Tool supports:
  - creation of a new project,
  - adding a new document into a project,
  - deletion of a document from a project.
- I want to: organize requirements in a tree document hierarchy with numbered sections
- So that: I can easily navigate in the document structure
- Status: Implemented
- Type: User Story

#### NEEDS-73: Table View
- As a(n): Editor
- Acceptance Criteria: Tool supports:
  - displaying of requirements in a table,
  - displaying requirements ID, description, discussion, links and custom attributes in columns,
  - hiding requirements table columns,
  - reordering of requirements table columns,
  - resizing of requirements table columns.
- I want to: display a table of requirements
- So that: I can review all requirements information in a single view
- Status: Implemented
- Type: User Story

#### NEEDS-74: Detailed View
- As a(n): Editor
- Acceptance Criteria: Tool supports:
  - displaying custom attributes of the selected requirement in a pane or dialog,
  - displaying discussion of the selected requirement in a pane or dialog,
  - displaying traceability links for the selected requirement in a pane or dialog,
  - displaying history of changes for the selected requirement in a pane or dialog.
- I want to: display all information about the selected requirement
- So that: I can display details about any requirement which are not visible in the requirements table
- Status: Implemented
- Type: User Story

#### NEEDS-17: Attachments
- As a(n): Editor
- Acceptance Criteria: Tool supports:
  - attachment of image file to document objects,
  - displaying image attachments in the context of the related document object,
  - deletion of attachments
- I want to: attach images and other documents to requirements
- So that: I can enhance textual requirements with visual content such as mockups, diagrams, etc.
- Status: Implemented
- Type: User Story

#### NEEDS-35: Sort
- As a(n): Editor
- Acceptance Criteria: Tool supports sorting requirements by:
  - the natural document order,
  - value of a custom attribute.
- I want to: order requirements by a chosen custom attribute
- So that: I can display requirements sorted by priority, risk, effort, etc.
- Status: Planned
- Type: User Story

### NEEDS-70: Manage Requirements
- Type: Epic

#### NEEDS-19: Custom Attributes Configuration
- As a(n): Architect
- Acceptance Criteria: Tool supports:
  - creation of a new custom attribute,
  - deletion of a custom attribute,
  - definition of following custom attribute types
  - number
  - date
  - boolean
  - single and multivalue enumeration
  - string / rich formatted text
- I want to: define additional requirements attributes
- So that: the document can flexibly store additional requirement properties, such as requirement source, priority, status, etc.
- Status: Verified
- Type: User Story

#### NEEDS-69: Custom Attributes
- As a(n): Editor
- Acceptance Criteria: Tool supports:
  - setting requirements source, priority, status and acceptance criteria
  - setting and resetting a value of a custom attribute for multiple requirements
- I want to: set a value of a chosen custom attribute for one or more selected requirements
- So that: I can define additional requirements properties, such as requirements source, prioritize requirements, manage requirement status, define acceptance criteria, etc.
- Status: Verified
- Type: User Story

#### NEEDS-16: Traceability Configuration
- As a(n): Architect
- Acceptance Criteria: Tool supports:
  - creation of at least one link type
  - definition of a start and end role for a link type
  - removal of a link type including all existing links
- I want to: define types of relationships between requirements
- So that: users can perform traceability analysis for a chosen group of links
- Status: Implemented
- Type: User Story

#### NEEDS-21: Traceability Links
- As a(n): Editor
- Acceptance Criteria: Tool supports:
  - creation of links with chosen link type between selected requirements,
  - deletion of links
- I want to: link related requirements
- So that: I can analyze requirements coverage, gap in requirements and impact of requirement changes.
- Status: Implemented
- Type: User Story

#### NEEDS-34: Filter
- As a(n): Editor
- Acceptance Criteria: Tool supports filtering requirements:
  - by full text search in the object heading, text or a custom attribute
  - with the given traceability link type
  - in the given section
- I want to: filter requirements
- So that: I can identify and manipulate requirements matching a condition
- Status: Implemented
- Type: User Story

#### NEEDS-36: Search
- As a(n): Editor
- Acceptance Criteria: Tool supports searching requirements containing a given keyword.
- I want to: find keywords
- So that: I can identify and manipulate requirements containing the searched keyword(s)
- Status: Implemented
- Type: User Story

### NEEDS-22: Review Requirements
- Type: Epic

#### NEEDS-24: Discussion
- As a(n): Reviewer
- Acceptance Criteria: Tool supports:
  - commenting a selected requirement,
  - displaying discussion for a selected requirement.
- I want to: comment requirements
- So that: I can provide feedback during requirements review
- Status: Implemented
- Type: User Story

#### NEEDS-30: Traceability Browser
- As a(n): Reviewer
- Acceptance Criteria: Tool supports:
  - displaying linked requirements ordered by link type
  - changing focus to a selected requirement
  - filtering requirements with missing traceability links of a given link type
- I want to: trace related requirements
- So that: I can perform coverage, gap and change impact analysis
- Status: Implemented
- Type: User Story

#### NEEDS-29: Print
- As a(n): Reviewer
- Acceptance Criteria: Tool supports:
  - printing a document with the same layout as it is displayed,
  - saving the document as PDF with the same layout as it is displayed.
- I want to: print a document view
- So that: I can review requirements without the need to run the tool
- Status: Implemented
- Type: User Story

### NEEDS-31: Audit Trail
- Type: Epic

#### NEEDS-26: History of Changes
- As a(n): Editor
- Acceptance Criteria: Tool supports:
  - displaying history of changes for a selected requirement.
- I want to: list all requirement changes
- So that: I can understand how the requirement evolved in time
- Status: Implemented
- Type: User Story

#### NEEDS-23: Traceability Report
- As a(n): Reviewer
- Acceptance Criteria: Tool supports:
  - generation of a custom traceability report which visualizes end-to-end requirements traceability
- I want to: generate a traceability report
- So that: I can analyze coverage, gaps and impact of requirements changes
- Status: Implemented
- Type: User Story

### NEEDS-11: Integrations
- Type: Epic

#### NEEDS-27: Import from Word
- As a(n): Editor
- Acceptance Criteria: Tool supports:
  - import of MS Word HTML preserving structure of document sections and paragraphs and image attachments
  - pasting of a text or a HTML fragment to requirements description.
- I want to: import a requirements specification from a MS Word document
- So that: I can reuse existing requirements specifications or other structured documents
- Status: Implemented
- Type: User Story

#### NEEDS-71: Import from Excel
- As a(n): Editor
- Acceptance Criteria: Tool supports:
  - import of new requirements from a CSV file including custom attribute values
  - updating requirements from a CSV file including custom attribute values
- I want to: import requirements from a MS Excel spreadsheet
- So that: I can import or update list of requirements
- Status: Implemented
- Type: User Story

#### NEEDS-28: Export to Word
- As a(n): Editor
- Acceptance Criteria: Tool supports:
  - export of a document to a HTML file,
  - import of an exported HTML file to a MS Word document preserving requirements structure and content
- I want to: to export structured requirements specification to MS Word
- So that: I can share requirements specifications with users without the tool
- Status: Implemented
- Type: User Story

#### NEEDS-72: Export to CSV
- As a(n): Editor
- Acceptance Criteria: Tool supports:
  - export of filtered list of requirements to a CSV file.
- I want to: export filtered list of requirements to MS Excel
- So that: I can reuse or update requirements in another application
- Status: Implemented
- Type: User Story

#### NEEDS-80: Export to Jira
- As a(n): Editor
- Acceptance Criteria: Tool supports:
  - export of requirements from a document to Jira,
  - mapping type of requirements to Jira issue types,
  - setting Jira issue summary, description from ReqView id, heading and text attributes,
  - preserving values of other Jira issue fields updated by Jira users (iteration, owner, status),
  - preserving Jira links,
  - bidirectional navigation between exported ReqView requirements and corresponding Jira issues.
- I want to: export requirements to Jira
- So that: the development team can manage requirements implementation
- Status: Planned
- Type: User Story

#### NEEDS-81: Update from Jira
- As a(n): Editor
- Acceptance Criteria: Tool supports:
  - mapping Jira issue fields to ReqView attributes,
  - updating values of mapped attributes from corresponding Jira issue fields.
- I want to: update requirements by information from Jira
- So that: I can track the implementation status in ReqView
- Status: Planned
- Type: User Story

#### NEEDS-84: Export to ReqIF
- As a(n): Editor
- Acceptance Criteria: Tool supports:
  - exporting documents to the ReqIF format,
  - preserving requirements structure, format, attachments, attributes, and links between exported requirements,
  - compliance with OMG ReqIF standard.
- I want to: export document to the Requirements Interchange Format (ReqIF)
- So that: I can provide requirements in a standardized format to suppliers or other team members using other tools
- Status: Planned
- Type: User Story

#### NEEDS-82: Export to Enterprise Architect
- Status: New
- Type: User Story

#### NEEDS-83: Import from Enterprise Architect
- Status: New
- Type: User Story

## NEEDS-4: Constraints
- Type: Section

### NEEDS-39: Startup Time
- As a(n): Editor
- Acceptance Criteria: Tool starts in less than 10s even for large projects.
- I want to: quickly start the tool
- So that: I do not need to wait long time for editing a project
- Status: Verified
- Type: Constraint

### NEEDS-41: Edit Response Time
- As a(n): Editor
- Acceptance Criteria: Tool updates view after any edit operation in a document with 10000 requirements in less than 1s.
- I want to: edit effectively requirements in large documents
- So that: I can work without waiting for tool responses
- Status: Verified
- Type: Constraint

### NEEDS-44: Document Size
- As a(n): Editor
- Acceptance Criteria: Tool can store documents with 10000 requirements and 100 attachments of total size 100 MB.
- I want to: create large requirements specifications
- So that: I can capture all requirements in a single document even for complex system development projects
- Status: Verified
- Type: Constraint

### NEEDS-42: Security
- As a(n): Editor
- Acceptance Criteria: Tool does not send any project information to the internet without user consent.
- I want to: store confidential information in the tool
- So that: I can be sure that no confidential information is compromised
- Status: Verified
- Type: Constraint

### NEEDS-51: Compatibility
- As a(n): Editor
- Acceptance Criteria: Tool is installed and run on Windows, Linux and a Mac.
- I want to: install and run the tool on Windows, Linux or Mac operating system
- So that: I can use the tool on any desktop PC or notebook.
- Status: Verified
- Type: Constraint
