[DOCUMENT]
TITLE: Hello world doc

[GRAMMAR]
ELEMENTS:
- TAG: SECTION
  PROPERTIES:
    IS_COMPOSITE: True
  FIELDS:
  - TITLE: UID
    TYPE: String
    REQUIRED: False
  - TITLE: TITLE
    TYPE: String
    REQUIRED: False
- TAG: TEXT
  FIELDS:
  - TITLE: STATEMENT
    TYPE: String
    REQUIRED: True
- TAG: REQUIREMENT
  FIELDS:
  - TITLE: STATEMENT
    TYPE: String
    REQUIRED: True
  - TITLE: RATIONALE
    TYPE: String
    REQUIRED: True
  - TITLE: COMMENT
    TYPE: String
    REQUIRED: True
  - TITLE: CUSTOM_FIELD
    TYPE: String
    REQUIRED: True

[[SECTION]]
TITLE: Referencing section

[TEXT]
STATEMENT: >>>
[LINK: SECTION]
<<<

[REQUIREMENT]
STATEMENT: >>>
[LINK: SECTION]
<<<
RATIONALE: [LINK: SECTION]
COMMENT: [LINK: SECTION]
COMMENT: [LINK: SECTION]
CUSTOM_FIELD: [LINK: SECTION]

[[/SECTION]]
