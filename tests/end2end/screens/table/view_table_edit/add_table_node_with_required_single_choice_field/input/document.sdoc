[DOCUMENT]
TITLE: Document

[GRAMMAR]
ELEMENTS:
- TAG: TEST_CASE
  FIELDS:
  - TITLE: UID
    TYPE: String
    REQUIRED: False
  - TITLE: STATUS
    TYPE: SingleChoice(Draft, Active)
    REQUIRED: True
  - TITLE: TITLE
    TYPE: String
    REQUIRED: False

[TEST_CASE]
UID: TEST-1
STATUS: Draft
TITLE: Existing test case
