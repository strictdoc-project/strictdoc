[DOCUMENT]
TITLE: Test Document
OPTIONS:
  REQUIREMENT_STYLE: Inline
  DEFAULT_VIEW: PRINT_VIEW
VIEWS:
- ID: PRINT_VIEW
  NAME: Print view
  TAGS:
  - OBJECT_TYPE: EXISTING_OBJECT
    VISIBLE_FIELDS:
    - NAME: UID
      PLACEMENT: XYZ
    - NAME: STATEMENT
    - NAME: RATIONALE

[GRAMMAR]
ELEMENTS:
- TAG: EXISTING_OBJECT
  FIELDS:
  - TITLE: UID
    TYPE: String
    REQUIRED: False
  - TITLE: TITLE
    TYPE: String
    REQUIRED: True
  - TITLE: STATEMENT
    TYPE: String
    REQUIRED: True
  - TITLE: RATIONALE
    TYPE: String
    REQUIRED: True
