[DOCUMENT]
TITLE: Document Two

[REQUIREMENT]
UID: REQ-101
TITLE: Other document requirement
STATEMENT: The system shall do a third thing.

[REQUIREMENT]
UID: REQ-003
TITLE: Third requirement
STATEMENT: The system shall do a third thing.

[REQUIREMENT]
UID: REQ-001
TITLE: First requirement
STATEMENT: The system shall do the first thing.
