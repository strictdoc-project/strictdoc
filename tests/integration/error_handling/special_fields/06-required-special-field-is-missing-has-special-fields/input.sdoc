[DOCUMENT]
TITLE: Hello world doc
SPECIAL_FIELDS:
- NAME: ECSS_COMPLIANCE
  TYPE: String
  REQUIRED: Yes
- NAME: ECSS_VERIFICATION
  TYPE: String
  REQUIRED: Yes
- NAME: PRIORITY
  TYPE: String

[REQUIREMENT]
SPECIAL_FIELDS:
  PRIORITY: High
TITLE: Req 1
