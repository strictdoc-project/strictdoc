[DOCUMENT]
TITLE: Test document

[GRAMMAR]
ELEMENTS:
- TAG: REQUIREMENT
  FIELDS:
  - TITLE: CHOICE_FIELD
    TYPE: SingleChoice(AAA, BBB, CCC, DDD)
    REQUIRED: True

[REQUIREMENT]
CHOICE_FIELD: AAA
