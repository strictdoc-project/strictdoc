[DOCUMENT]
NAME: StrictDoc

[SECTION]
LEVEL: 1
TITLE: High-level Requirements

[REQUIREMENT]
UID: SDOC-HIGH-REQS-MANAGEMENT
TITLE: Requirements management
STATEMENT: StrictDoc shall enable requirements management.

[REQUIREMENT]
UID: SDOC-HIGH-DATA-MODEL
TITLE: Data model
STATEMENT: StrictDoc shall be based on a well-defined data model.
COMMENT: >>>
StrictDoc is a result of multiple attempts to find a solution for working with
text-based requirements:

- Doorstop
- StrictDoc, first generation: Markdown-based C++ program.
- StrictDoc, second generation: RST/Sphinx-based Python program. Using Sphinx
extensions to manage meta information.
<<<

[REQUIREMENT]
TITLE: Requirements validation
STATEMENT: StrictDoc shall allow validation of requirement documents.

[REQUIREMENT]
TITLE: Requirements text format
STATEMENT: StrictDoc shall allow storage of requirements in text form.

[REQUIREMENT]
TITLE: Linking requirements
STATEMENT: StrictDoc shall support linking requirements to each other.

[REQUIREMENT]
UID: SDOC-HIGH-REQS-TRACEABILITY
TITLE: Traceability
STATEMENT: StrictDoc shall support traceability of requirements.

[REQUIREMENT]
TITLE: Visualization
STATEMENT: StrictDoc shall provide means for visualization of requirement documents.

[REQUIREMENT]
TITLE: Open Source software
STATEMENT: StrictDoc shall always be free and open source software.

[/SECTION]

[SECTION]
LEVEL: 1
TITLE: Data Model

[REQUIREMENT]
UID: SDOC-DM-001
REFS:
- TYPE: Parent
  VALUE: SDOC-HIGH-REQS-MANAGEMENT
TITLE: Modeling capability
STATEMENT: StrictDoc's Data Model shall accommodate for maximum possible standard requirement document formats.
BODY: >>>
Examples of standard requirements documents include but are not limited to:
- ESA Statement of Work documents
<<<

[SECTION]
LEVEL: 2
TITLE: Requirement item

[REQUIREMENT]
TITLE: Statement
STATEMENT: Requirement item shall have a statement.

[REQUIREMENT]
TITLE: Content body
STATEMENT: Requirement item might have an content body.

[REQUIREMENT]
TITLE: UID identifier
STATEMENT: Requirement item might have an UID identifier.

[REQUIREMENT]
TITLE: Title
STATEMENT: Requirement item might have an title.

[REQUIREMENT]
TITLE: References
STATEMENT: Requirement item might have one or more references.

[REQUIREMENT]
TITLE: Comments
STATEMENT: Requirement item might have one or more comments.

[/SECTION]

[/SECTION]

[SECTION]
LEVEL: 1
TITLE: Requirements Document Format

[REQUIREMENT]
UID: SDOC-RDF-001
REFS:
- TYPE: Parent
  VALUE: SDOC-DM-001
TITLE: Primary text implementation
STATEMENT: StrictDoc RDF shall serve as a text-based implementation of the Strict Doc Data Model.

[REQUIREMENT]
TITLE: Grammar
STATEMENT: StrictDoc RDF shall provide a fixed grammar structure.

[REQUIREMENT]
TITLE: Type safety
STATEMENT: StrictDoc RDF shall enable type-safe parsing of requirement documents.

[/SECTION]

[SECTION]
LEVEL: 1
TITLE: HTML Export

[REQUIREMENT]
TITLE: Single document: Normal form
STATEMENT: StrictDoc shall export single document pages in a normal document-like form.

[REQUIREMENT]
TITLE: Single document: Tabular form
STATEMENT: StrictDoc shall export single document pages in a tabular form.

[REQUIREMENT]
REFS:
- TYPE: Parent
  VALUE: SDOC-HIGH-REQS-TRACEABILITY
TITLE: Single document: 1-level traceability
STATEMENT: StrictDoc shall export 1-level traceability document.

[REQUIREMENT]
REFS:
- TYPE: Parent
  VALUE: SDOC-HIGH-REQS-TRACEABILITY
TITLE: Single document: Deep traceability
STATEMENT: StrictDoc shall export deep traceability document.

[/SECTION]

[SECTION]
LEVEL: 1
TITLE: PDF Export

[REQUIREMENT]
TITLE: Sphinx documentation generator
STATEMENT: StrictDoc shall support exporting documents to Sphinx/RST format.

[/SECTION]
