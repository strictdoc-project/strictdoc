[DOCUMENT]
TITLE: Hello world doc
VERSION: @GIT_VERSION, @GIT_BRANCH
DATE: @GIT_COMMIT_DATE, @GIT_COMMIT_DATETIME
METADATA:
  GIT_VERSION: @GIT_VERSION
  GIT_BRANCH: @GIT_BRANCH
  GIT_COMMIT_DATE: @GIT_COMMIT_DATE
  GIT_COMMIT_DATETIME: @GIT_COMMIT_DATETIME
