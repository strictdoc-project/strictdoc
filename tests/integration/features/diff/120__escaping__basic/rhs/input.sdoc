[DOCUMENT]
TITLE: Doc Title with more special characters <>&"'

[[SECTION]]
TITLE: Added section with more special characters <>&"'

[REQUIREMENT]
TITLE: Added title with more special characters <>&"'
STATEMENT: Added statement with more special characters <>&"'

[[/SECTION]]

[[SECTION]]
UID: SECT-1
TITLE: Changed section with more special characters <>&"'

[REQUIREMENT]
UID: REQ-1
TITLE: Changed title with more special characters <>&"'
STATEMENT: Changed statement with more special characters <>&"'

[[/SECTION]]
