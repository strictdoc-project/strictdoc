[DOCUMENT]
TITLE: Document title

[TEXT]
STATEMENT: >>>
Hello world!
<<<

[[SECTION]]
TITLE: Section 1 title

[TEXT]
STATEMENT: >>>
This is a free text of this section 1.
<<<

[[SECTION]]
TITLE: Nested section 1 title

[TEXT]
STATEMENT: >>>
This is a free text of this nested section 1.
<<<

[[SECTION]]
TITLE: Nested section 11 title

[TEXT]
STATEMENT: >>>
This is a free text of this nested section 11.
<<<

[[/SECTION]]

[[/SECTION]]

[[/SECTION]]

[[SECTION]]
TITLE: Section 2 title

[TEXT]
STATEMENT: >>>
This is a free text of this section 2.
<<<

[[SECTION]]
TITLE: Nested section 2 title

[TEXT]
STATEMENT: >>>
This is a free text of this nested section 2.
<<<

[[/SECTION]]

[[/SECTION]]
