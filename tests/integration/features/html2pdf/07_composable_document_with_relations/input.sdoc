[DOCUMENT]
TITLE: Project Risk Management
UID: PARENT-DOC

[TEXT]
STATEMENT: Main file

[DOCUMENT_FROM_FILE]
FILE: nested/included.sdoc

[REQUIREMENT]
UID: REQ-003
TITLE: Third one
STATEMENT: >>>
Link from parent document to parent document: [LINK: PARENT-DOC]

Link from parent document to included document: [LINK: INCLUDED-DOC]

Link from parent document to this document's requiremnt: [LINK: REQ-004]
<<<

[REQUIREMENT]
UID: REQ-004
TITLE: fourth one
STATEMENT: >>>
The fourth statement
<<<
