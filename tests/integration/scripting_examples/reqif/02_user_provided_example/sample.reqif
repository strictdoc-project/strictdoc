# ...Anonymized-8393017329...

# Specification: ...Anonymized-3908282161...
- Link to Regulation and SI: ...Anonymized-5665086549...

## R1
...Anonymized-800094403...
- AuReOn-Source ID: ...Anonymized-3485941762...
- Link to Regulation and SI: ...Anonymized-5486385466...
- Version Number: ...Anonymized-658922315...
- Markets/Regions: ...Anonymized-7892866527...
- Artifact Type: Heading
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

## R2
...Anonymized-1296777781...
- AuReOn-Source ID: ...Anonymized-7588743596...
- Link to Regulation and SI: ...Anonymized-8431163323...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R3
...Anonymized-8777602262...
- AuReOn-Source ID: ...Anonymized-1343763567...
- Link to Regulation and SI: ...Anonymized-9838388979...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

## R4
...Anonymized-3863645040...
- AuReOn-Source ID: ...Anonymized-2256138007...
- Link to Regulation and SI: ...Anonymized-5517487880...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

### R5
...Anonymized-1479856220...
- AuReOn-Source ID: ...Anonymized-317796541...
- Link to Regulation and SI: ...Anonymized-7832459769...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R6
...Anonymized-8115727826...
- AuReOn-Source ID: ...Anonymized-8905046851...
- Link to Regulation and SI: ...Anonymized-5348911902...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R7
...Anonymized-1259839806...
- AuReOn-Source ID: ...Anonymized-6479995737...
- Link to Regulation and SI: ...Anonymized-7502866506...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R8
...Anonymized-9464678217...
- AuReOn-Source ID: ...Anonymized-1422871779...
- Link to Regulation and SI: ...Anonymized-8941615821...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R9
...Anonymized-3739062049...
- AuReOn-Source ID: ...Anonymized-7546681705...
- Link to Regulation and SI: ...Anonymized-9216441948...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R10
...Anonymized-6410369870...
- AuReOn-Source ID: ...Anonymized-9651909560...
- Link to Regulation and SI: ...Anonymized-9495790459...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R11
...Anonymized-7525179202...
- AuReOn-Source ID: ...Anonymized-3299295216...
- Link to Regulation and SI: ...Anonymized-2391387957...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R12
...Anonymized-7269471756...
- AuReOn-Source ID: ...Anonymized-9988603806...
- Link to Regulation and SI: ...Anonymized-531577127...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R13
...Anonymized-5147026012...
- AuReOn-Source ID: ...Anonymized-1610382840...
- Link to Regulation and SI: ...Anonymized-2348957216...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R14
...Anonymized-6347952334...
- AuReOn-Source ID: ...Anonymized-9508205917...
- Link to Regulation and SI: ...Anonymized-4639692023...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R15
...Anonymized-941514812...
- AuReOn-Source ID: ...Anonymized-2884772276...
- Link to Regulation and SI: ...Anonymized-6140772820...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R16
...Anonymized-3218863434...
- AuReOn-Source ID: ...Anonymized-1485701735...
- Link to Regulation and SI: ...Anonymized-2237412091...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R17
...Anonymized-3059328087...
- AuReOn-Source ID: ...Anonymized-2809540798...
- Link to Regulation and SI: ...Anonymized-1704844988...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R18
...Anonymized-3136273741...
- AuReOn-Source ID: ...Anonymized-7807376038...
- Link to Regulation and SI: ...Anonymized-4103706070...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R19
...Anonymized-9949067721...
- AuReOn-Source ID: ...Anonymized-850084807...
- Link to Regulation and SI: ...Anonymized-7817490845...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R20
...Anonymized-3075536904...
- AuReOn-Source ID: ...Anonymized-6720767375...
- Link to Regulation and SI: ...Anonymized-2028548567...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R21
...Anonymized-4372756441...
- AuReOn-Source ID: ...Anonymized-4130035793...
- Link to Regulation and SI: ...Anonymized-7671838599...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R22
...Anonymized-5512684929...
- AuReOn-Source ID: ...Anonymized-3616013271...
- Link to Regulation and SI: ...Anonymized-4308927700...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R23
...Anonymized-6887034286...
- AuReOn-Source ID: ...Anonymized-7806146762...
- Link to Regulation and SI: ...Anonymized-2545287623...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R24
...Anonymized-7554940541...
- AuReOn-Source ID: ...Anonymized-5968203633...
- Link to Regulation and SI: ...Anonymized-3920978095...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R25
...Anonymized-1619523204...
- AuReOn-Source ID: ...Anonymized-4609609126...
- Link to Regulation and SI: ...Anonymized-4528894250...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R26
...Anonymized-1789134926...
- AuReOn-Source ID: ...Anonymized-3250294175...
- Link to Regulation and SI: ...Anonymized-3948870981...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R27
...Anonymized-6917232909...
- AuReOn-Source ID: ...Anonymized-5751309903...
- Link to Regulation and SI: ...Anonymized-3089142669...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

#### R28
...Anonymized-9340854717...
- AuReOn-Source ID: ...Anonymized-9904326205...
- Link to Regulation and SI: ...Anonymized-3639332026...
- Version Number: ...Anonymized-658922315...
- Markets/Regions: ...Anonymized-7892866527...
- Artifact Type: Definition
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00

## R29
...Anonymized-6898346570...
- AuReOn-Source ID: ...Anonymized-9040039960...
- Link to Regulation and SI: ...Anonymized-5341687464...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R30
...Anonymized-2436964642...
- AuReOn-Source ID: ...Anonymized-622526346...
- Link to Regulation and SI: ...Anonymized-645987737...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R31
...Anonymized-1808923387...
- AuReOn-Source ID: ...Anonymized-3084599363...
- Link to Regulation and SI: ...Anonymized-1574351206...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R32
...Anonymized-7068117402...
- AuReOn-Source ID: ...Anonymized-2991775691...
- Link to Regulation and SI: ...Anonymized-4194021414...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R33
...Anonymized-283673809...
- AuReOn-Source ID: ...Anonymized-1461367788...
- Link to Regulation and SI: ...Anonymized-1564167532...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

## R34
...Anonymized-5414531972...
- AuReOn-Source ID: ...Anonymized-8715649695...
- Link to Regulation and SI: ...Anonymized-1380800799...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R35
...Anonymized-9347299576...
- AuReOn-Source ID: ...Anonymized-6463227160...
- Link to Regulation and SI: ...Anonymized-608398224...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

## R36
...Anonymized-8068106365...
- AuReOn-Source ID: ...Anonymized-1703766920...
- Link to Regulation and SI: ...Anonymized-3913736367...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R37
...Anonymized-7000115537...
- AuReOn-Source ID: ...Anonymized-148261924...
- Link to Regulation and SI: ...Anonymized-3587905373...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R38
...Anonymized-7392950794...
- AuReOn-Source ID: ...Anonymized-7916997897...
- Link to Regulation and SI: ...Anonymized-6468103625...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R39
...Anonymized-6251844059...
- AuReOn-Source ID: ...Anonymized-7511992721...
- Link to Regulation and SI: ...Anonymized-514023902...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R40
...Anonymized-1258946577...
- AuReOn-Source ID: ...Anonymized-389543852...
- Link to Regulation and SI: ...Anonymized-1389169807...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R41
...Anonymized-9642852011...
- AuReOn-Source ID: ...Anonymized-9619304565...
- Link to Regulation and SI: ...Anonymized-7529840200...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

## R42
...Anonymized-1159585295...
- AuReOn-Source ID: ...Anonymized-7950910032...
- Link to Regulation and SI: ...Anonymized-9009228309...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R43
...Anonymized-2188523933...
- AuReOn-Source ID: ...Anonymized-8523562560...
- Link to Regulation and SI: ...Anonymized-4865879573...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

## R44
...Anonymized-8869565931...
- AuReOn-Source ID: ...Anonymized-252231026...
- Link to Regulation and SI: ...Anonymized-7887334775...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R45
...Anonymized-9655006692...
- AuReOn-Source ID: ...Anonymized-8891100199...
- Link to Regulation and SI: ...Anonymized-9928146833...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R46
...Anonymized-173903207...
- AuReOn-Source ID: ...Anonymized-3084470049...
- Link to Regulation and SI: ...Anonymized-7135009558...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R47
...Anonymized-4437392108...
- AuReOn-Source ID: ...Anonymized-3118801069...
- Link to Regulation and SI: ...Anonymized-7552041697...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R48
...Anonymized-7231710889...
- AuReOn-Source ID: ...Anonymized-5849658466...
- Link to Regulation and SI: ...Anonymized-2878691932...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

## R49
...Anonymized-3856771626...
- AuReOn-Source ID: ...Anonymized-5715497394...
- Link to Regulation and SI: ...Anonymized-2023971846...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R50
...Anonymized-1552650554...
- AuReOn-Source ID: ...Anonymized-1939782211...
- Link to Regulation and SI: ...Anonymized-3225094010...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R51
...Anonymized-2027681480...
- AuReOn-Source ID: ...Anonymized-9561322261...
- Link to Regulation and SI: ...Anonymized-949459526...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R52
...Anonymized-8576707282...
- AuReOn-Source ID: ...Anonymized-5739100047...
- Link to Regulation and SI: ...Anonymized-6041780675...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R53
...Anonymized-8321981209...
- AuReOn-Source ID: ...Anonymized-8850002530...
- Link to Regulation and SI: ...Anonymized-9531173380...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R54
...Anonymized-9387935987...
- AuReOn-Source ID: ...Anonymized-6994900004...
- Link to Regulation and SI: ...Anonymized-5705046574...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R55
...Anonymized-7023507353...
- AuReOn-Source ID: ...Anonymized-7547846617...
- Link to Regulation and SI: ...Anonymized-273974890...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R56
...Anonymized-7298310144...
- AuReOn-Source ID: ...Anonymized-7400707214...
- Link to Regulation and SI: ...Anonymized-1981589209...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R57
...Anonymized-1075256361...
- AuReOn-Source ID: ...Anonymized-4535043754...
- Link to Regulation and SI: ...Anonymized-4040398390...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R58
...Anonymized-6138260782...
- AuReOn-Source ID: ...Anonymized-3220439109...
- Link to Regulation and SI: ...Anonymized-859469674...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R59
...Anonymized-5647998407...
- AuReOn-Source ID: ...Anonymized-4408062050...
- Link to Regulation and SI: ...Anonymized-1861588527...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R60
...Anonymized-4308580990...
- AuReOn-Source ID: ...Anonymized-2101621627...
- Link to Regulation and SI: ...Anonymized-4788743746...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R61
...Anonymized-2137374419...
- AuReOn-Source ID: ...Anonymized-773468615...
- Link to Regulation and SI: ...Anonymized-1592783987...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R62
...Anonymized-1428791751...
- AuReOn-Source ID: ...Anonymized-7353724101...
- Link to Regulation and SI: ...Anonymized-2678501331...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R63
...Anonymized-9676532582...
- AuReOn-Source ID: ...Anonymized-5843515385...
- Link to Regulation and SI: ...Anonymized-9051607315...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R64
...Anonymized-1968810068...
- AuReOn-Source ID: ...Anonymized-5747795401...
- Link to Regulation and SI: ...Anonymized-4746637949...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R65
...Anonymized-952321743...
- AuReOn-Source ID: ...Anonymized-2737858268...
- Link to Regulation and SI: ...Anonymized-7452442765...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R66
...Anonymized-4385285431...
- AuReOn-Source ID: ...Anonymized-5472257823...
- Link to Regulation and SI: ...Anonymized-1989344787...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R67
...Anonymized-2306522878...
- AuReOn-Source ID: ...Anonymized-5876716670...
- Link to Regulation and SI: ...Anonymized-6824723755...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

## R68
...Anonymized-4975961063...
- AuReOn-Source ID: ...Anonymized-9130840042...
- Link to Regulation and SI: ...Anonymized-9808952992...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R69
...Anonymized-5731851921...
- AuReOn-Source ID: ...Anonymized-9568165697...
- Link to Regulation and SI: ...Anonymized-7542791956...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R70
...Anonymized-5314675155...
- AuReOn-Source ID: ...Anonymized-6048954434...
- Link to Regulation and SI: ...Anonymized-1829965826...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R71
...Anonymized-7947804285...
- AuReOn-Source ID: ...Anonymized-4009752199...
- Link to Regulation and SI: ...Anonymized-4558995029...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R72
...Anonymized-3454865771...
- AuReOn-Source ID: ...Anonymized-1490070575...
- Link to Regulation and SI: ...Anonymized-7700975833...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R73
...Anonymized-6803295887...
- AuReOn-Source ID: ...Anonymized-8501341331...
- Link to Regulation and SI: ...Anonymized-283088309...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R74
...Anonymized-9889542268...
- AuReOn-Source ID: ...Anonymized-7651962356...
- Link to Regulation and SI: ...Anonymized-9871749776...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R75
...Anonymized-908130948...
- AuReOn-Source ID: ...Anonymized-6533294417...
- Link to Regulation and SI: ...Anonymized-9054608968...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R76
...Anonymized-716334318...
- AuReOn-Source ID: ...Anonymized-3826160720...
- Link to Regulation and SI: ...Anonymized-7937129434...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R77
...Anonymized-5835886909...
- AuReOn-Source ID: ...Anonymized-9754342784...
- Link to Regulation and SI: ...Anonymized-4486780515...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

## R78
...Anonymized-8411277964...
- AuReOn-Source ID: ...Anonymized-7549707755...
- Link to Regulation and SI: ...Anonymized-8194610651...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R79
...Anonymized-1138792890...
- AuReOn-Source ID: ...Anonymized-2615369854...
- Link to Regulation and SI: ...Anonymized-567001839...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R80
...Anonymized-4939431975...
- AuReOn-Source ID: ...Anonymized-3848389381...
- Link to Regulation and SI: ...Anonymized-2482107900...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R81
...Anonymized-5404371533...
- AuReOn-Source ID: ...Anonymized-7855129612...
- Link to Regulation and SI: ...Anonymized-266519439...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R82
...Anonymized-5139386584...
- AuReOn-Source ID: ...Anonymized-9081336126...
- Link to Regulation and SI: ...Anonymized-5586217396...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R83
...Anonymized-3139452980...
- AuReOn-Source ID: ...Anonymized-3187410679...
- Link to Regulation and SI: ...Anonymized-2815424808...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

## R84
...Anonymized-2731172538...
- AuReOn-Source ID: ...Anonymized-687056417...
- Link to Regulation and SI: ...Anonymized-271997068...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R85
...Anonymized-7204634363...
- AuReOn-Source ID: ...Anonymized-2911421316...
- Link to Regulation and SI: ...Anonymized-987624080...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R86
...Anonymized-9879655889...
- AuReOn-Source ID: ...Anonymized-9831278927...
- Link to Regulation and SI: ...Anonymized-1453249950...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R87
...Anonymized-5380229692...
- AuReOn-Source ID: ...Anonymized-2192263156...
- Link to Regulation and SI: ...Anonymized-5394617573...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

#### R88
...Anonymized-9303550356...
- AuReOn-Source ID: ...Anonymized-5808096669...
- Link to Regulation and SI: ...Anonymized-7409642205...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R89
...Anonymized-7775127350...
- AuReOn-Source ID: ...Anonymized-6980915407...
- Link to Regulation and SI: ...Anonymized-2022967872...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R90
...Anonymized-4451010361...
- AuReOn-Source ID: ...Anonymized-9237036141...
- Link to Regulation and SI: ...Anonymized-7276482119...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R91
...Anonymized-6890198797...
- AuReOn-Source ID: ...Anonymized-3150536994...
- Link to Regulation and SI: ...Anonymized-2168813507...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R92
...Anonymized-6432327145...
- AuReOn-Source ID: ...Anonymized-337191821...
- Link to Regulation and SI: ...Anonymized-6895298795...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R93
...Anonymized-8820416554...
- AuReOn-Source ID: ...Anonymized-9619923204...
- Link to Regulation and SI: ...Anonymized-7611461529...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R94
...Anonymized-5571156336...
- AuReOn-Source ID: ...Anonymized-6205776186...
- Link to Regulation and SI: ...Anonymized-325089777...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

## R95
...Anonymized-104571040...
- AuReOn-Source ID: ...Anonymized-4311640846...
- Link to Regulation and SI: ...Anonymized-1273901455...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...

### R96
...Anonymized-4320228361...
- AuReOn-Source ID: ...Anonymized-4082451084...
- Link to Regulation and SI: ...Anonymized-8178489555...
- Version Number: ...Anonymized-658922315...
- Markets/Regions: ...Anonymized-7892866527...
- Artifact Type: Requirement
- Supplemental Information: false
- Supplemental Information - Modification Date: 1970-01-01T00:00:01
- Regulation Number: ...Anonymized-7226856433...
- Regulation Status: Final
- Vehicle Category: Buses (all) | buses (general), Trucks (all) | trucks (general), PCs (all) | PCs (general)
- Effective Date: 2018-12-27T00:00:00
- Technical Compliance Relevance: ...Anonymized-3560788266...
