[DOCUMENT]
TITLE: Hello world doc #1

[GRAMMAR]
ELEMENTS:
- TAG: REQUIREMENT
  FIELDS:
  - TITLE: UID
    TYPE: String
    REQUIRED: True
  - TITLE: TITLE
    TYPE: String
    REQUIRED: True
  - TITLE: STATEMENT
    TYPE: String
    REQUIRED: True
  RELATIONS:
  - TYPE: Parent
    ROLE: REQUIREMENT_FOR
  - TYPE: File

[REQUIREMENT]
UID: REQ1-001
TITLE: Requirement Title #1
STATEMENT: Requirement Statement #1

[REQUIREMENT]
UID: REQ1-002
TITLE: Requirement Title #2
STATEMENT: Requirement Statement #2

[REQUIREMENT]
UID: REQ1-003
TITLE: Requirement Title #3
STATEMENT: Requirement Statement #3
