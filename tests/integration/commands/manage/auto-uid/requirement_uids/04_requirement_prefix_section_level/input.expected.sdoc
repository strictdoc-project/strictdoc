[DOCUMENT]
TITLE: Hello world doc
REQ_PREFIX: DOC-

[SECTION]
UID: SECTION-HWD-Section-1
TITLE: Section 1
REQ_PREFIX: LEVEL1-REQ-

[REQUIREMENT]
UID: LEVEL1-REQ-1
STATEMENT: System shall do L1-1.

[REQUIREMENT]
UID: LEVEL1-REQ-2
STATEMENT: System shall do L1-1.

[/SECTION]

[SECTION]
UID: SECTION-HWD-Section-2
TITLE: Section 2
REQ_PREFIX: LEVEL2-REQ-

[REQUIREMENT]
UID: LEVEL2-REQ-2
STATEMENT: System shall do L2-1.

[REQUIREMENT]
UID: LEVEL2-REQ-1
STATEMENT: System shall do L2-1.

[/SECTION]
