# Documentation export by StrictDoc

# Specification: Sample ReqIF document

## R1: Section #1 (SECTION)

### REQ-001: Requirement #1 (REQUIREMENT)

### REQ-002: Requirement #2 (REQUIREMENT)
- Parent -> REQ-001
