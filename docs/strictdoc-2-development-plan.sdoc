[DOCUMENT]
TITLE: Development Plan
OPTIONS:
  REQUIREMENT_STYLE: Table
  REQUIREMENT_IN_TOC: True

[FREETEXT]
This document presents the goals of the StrictDoc project and describes how the
project is developed.
[/FREETEXT]

[SECTION]
TITLE: Project goals

[FREETEXT]
StrictDoc is an attempt to create an open source tool for writing
technical requirements specifications.
[/FREETEXT]

[REQUIREMENT]
UID: GOAL-1-TOOL-SUPPORT
TITLE: Software support for writing requirements and specifications documents
STATEMENT: >>>
There shall exist free and lightweight yet capable software for writing
requirements and specifications documents
<<<
COMMENT: >>>
Technical documentation is hard, it can be an extremely laborious process.
Software shall support engineers in their work with documentation.
<<<

[REQUIREMENT]
UID: GOAL-2-REDUCE-DOCUMENTATION-HAZARDS
TITLE: Reduce documentation hazards
STATEMENT: >>>
There shall exist no (or less) opportunity for writing incorrect or inconsistent
documentation.
<<<
COMMENT: >>>
Every serious engineering activity, such as safety engineering or systems
engineering, starts with requirements. The more critical is a product the higher
the importance of good documentation.

Technical documentation can be and often becomes a source of hazards.
It is recognized that many failures stem from inadequate requirements
engineering. While it is not possible to fix the problem of inadequate
requirements engineering in general, it is definitely possible to improve
software that supports engineers in activities such as requirements engineering
and writing technical documentation.
<<<

[REQUIREMENT]
UID: GOAL-3-NO-RUNAWAY-DOCUMENTATION
TITLE: No (or less) run-away documentation
STATEMENT: Software shall support engineers in keeping documentation up-to-date.
COMMENT: >>>
Technical documentation easily becomes outdated. Many existing tools for
documentation do not provide any measures for ensuring overall consistency of
documents and documentation trees.
<<<

[REQUIREMENT]
UID: GOAL-4-CHANGE-MANAGEMENT
TITLE: Change management
STATEMENT: Software shall provide capabilities for change management and impact assessment.
COMMENT: >>>
Change management is difficult. The bigger the project is, the harder it is to
maintain its documentation. If a change is introduced to a project, it usually
requires a full revision of its requirements.
<<<
COMMENT: >>>
When the basic capabilities of StrictDoc are in place, it should be possible
to do a more advanced analysis of requirements and requirement trees:

- Finding similar or relevant requirements.
- Enforce invariants that should be hold. Example: mass or power budget.
<<<

[/SECTION]

[SECTION]
TITLE: User interfaces

[FREETEXT]
There are two user interfaces for StrictDoc:

1) Command-line interface (CLI)
2) Web interface

The CLI interface is already developed, the web interface is (slow)
work-in-progress.
[/FREETEXT]

[REQUIREMENT]
UID: UI-1-TEXT
TITLE: Command-line interface
STATEMENT: >>>
StrictDoc shall provide a command-line interface.
<<<

[REQUIREMENT]
UID: UI-2-WEB
TITLE: Web interface
STATEMENT: >>>
StrictDoc shall provide a web interface.
<<<

[/SECTION]

[SECTION]
TITLE: Development team

[FREETEXT]
StrictDoc is a spare time project developed and maintained by two people
with occasional contributions from the Open Source community.
[/FREETEXT]

[/SECTION]
