[DOCUMENT]
TITLE: Hello world doc 2

[REQUIREMENT]
UID: REQ-S1
TITLE: Req #S1
STATEMENT: >>>
This is REQ-1.
System shall do #1.
System shall do #1.
System shall do #1.
System shall do #1.
System shall do #1.
System shall do #1.
System shall do #1.
System shall do #1.
System shall do #1.
System shall do #1.
System shall do #1.
System shall do #1.
System shall do #1.
System shall do #1.
<<<

[REQUIREMENT]
UID: REQ-S2
TITLE: Req #S2
STATEMENT: System shall do #2.

[REQUIREMENT]
UID: REQ-S3
TITLE: Req #S3
STATEMENT: System shall do #3.
