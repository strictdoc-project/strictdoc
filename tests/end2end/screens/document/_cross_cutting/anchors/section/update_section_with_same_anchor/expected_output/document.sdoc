[DOCUMENT]
TITLE: Document 1

[FREETEXT]
Hello world!
[/FREETEXT]

[SECTION]
TITLE: Modified title

[FREETEXT]
Modified statement.

[ANCHOR: AD1]
[/FREETEXT]

[/SECTION]

[SECTION]
TITLE: Second section

[FREETEXT]
This is a free text of this section.
[/FREETEXT]

[/SECTION]
