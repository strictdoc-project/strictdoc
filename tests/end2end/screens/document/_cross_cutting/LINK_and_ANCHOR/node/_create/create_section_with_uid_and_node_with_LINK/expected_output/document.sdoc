[DOCUMENT]
TITLE: Document 1

[[SECTION]]
UID: SECT-1
TITLE: First title

[[/SECTION]]

[REQUIREMENT]
UID: REQ-1
TITLE: Second title
STATEMENT: >>>
This is a text of the requirement.

[LINK: SECT-1]
<<<
