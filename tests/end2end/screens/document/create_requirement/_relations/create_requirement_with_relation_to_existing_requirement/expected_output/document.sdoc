[DOCUMENT]
TITLE: Document 1

[REQUIREMENT]
UID: REQ-001
TITLE: Requirement #1 title
STATEMENT: Requirement #1 statement.

[REQUIREMENT]
UID: REQ-002
TITLE: Requirement #2 title
STATEMENT: >>>
Requirement #2 statement.
<<<
REFS:
- TYPE: Parent
  VALUE: REQ-001
