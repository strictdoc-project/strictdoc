[DOCUMENT]
NAME: Requirements

[SECTION]
LEVEL: 1
TITLE: Problems

[REQUIREMENT]
UID: PROBLEM-1-TOOLS
TITLE: Technical documentation software
STATEMENT: >>>
There shall exist free and lightweight yet capable software for technical
documentation.
<<<
COMMENT: >>>
The state of the art for many small companies working with
requirements: using Excel for requirements management in the projects with
hundreds or thousands of requirements.
<<<

[REQUIREMENT]
UID: PROBLEM-2-DOCUMENTATION-IS-HARD
TITLE: Technical documentation is hard
STATEMENT: >>>
Software shall support engineers in their work with documentation.
<<<
COMMENT: Technical documentation can be an extremely laborious process.

[REQUIREMENT]
UID: PROBLEM-3-DOCUMENTATION-AS-HAZARD
TITLE: Technical documentation as a source of hazards
STATEMENT: There shall exist no (or less) opportunity for writing incorrect documentation.
COMMENT: >>>
Every serious engineering activity, such as safety engineering or systems
engineering, starts with requirements. The more critical is a product the higher
the importance of good documentation.

It is recognized that many failures stem from inadequate requirements
engineering. While it is not possible to fix the problem of inadequate
requirements engineering in general, it is definitely possible to improve
software that supports engineers in activities such as requirements engineering
and writing technical documentation.
<<<

[REQUIREMENT]
UID: PROBLEM-4-OUTDATED-DOCUMENTATION
TITLE: Technical documentation easily becomes outdated
STATEMENT: Software shall support engineers in keeping documentation up-to-date.
COMMENT: >>>
Many existing tools for documentation do not provide any measures for
ensuring overall consistency of documents and documentation trees.
<<<

[REQUIREMENT]
UID: PROBLEM-5-CHANGE-MANAGEMENT
TITLE: Change management is difficult
STATEMENT: Software shall provide capabilities for change management and impact assessment.
COMMENT: >>>
The bigger the project is, the harder it is to maintain its documentation.
If a change is introduced to a project, it usually requires a full revision
of its requirements TBD.
<<<

[/SECTION]

[SECTION]
LEVEL: 1
TITLE: High-level requirements

[REQUIREMENT]
UID: SDOC-HIGH-REQS-MANAGEMENT
REFS:
- TYPE: Parent
  VALUE: PROBLEM-1-TOOLS
TITLE: Requirements management
STATEMENT: Saturn shall enable requirements management.

[REQUIREMENT]
UID: SDOC-HIGH-DATA-MODEL
TITLE: Data model
STATEMENT: Saturn shall be based on a well-defined data model.
COMMENT: >>>
Saturn is a result of multiple attempts to find a solution for working with
text-based requirements:

- Saturn, first generation: Markdown-based C++ program. Custom requirements
  metadata in YAML.
- Saturn, second generation: RST/Sphinx-based Python program. Using Sphinx
  extensions to manage meta information.

The result of these efforts is the realization that a text-based requirements
and specifications management tool TBD.
<<<

[REQUIREMENT]
TITLE: Command-line interface
STATEMENT: Saturn shall provide a command-line interface.

[REQUIREMENT]
TITLE: Requirements validation
STATEMENT: Saturn shall allow validation of requirement documents.

[REQUIREMENT]
TITLE: Requirements text format
STATEMENT: Saturn shall allow storage of requirements in a plain-text human readable form.

[REQUIREMENT]
TITLE: Linking requirements
STATEMENT: Saturn shall support linking requirements to each other.

[REQUIREMENT]
TITLE: Scalability
STATEMENT: Saturn shall allow working with large documents and document trees containing at least 10000 requirement items.

[REQUIREMENT]
UID: SDOC-HIGH-REQS-TRACEABILITY
TITLE: Traceability
STATEMENT: Saturn shall support traceability of requirements.

[REQUIREMENT]
TITLE: Visualization
STATEMENT: Saturn shall provide means for visualization of requirement documents.

[REQUIREMENT]
TITLE: Open source software
STATEMENT: Saturn shall always be free and open source software.

[/SECTION]

[SECTION]
LEVEL: 1
TITLE: Implementation requirements

[REQUIREMENT]
UID: SDOC-IMPL-PARAL
TITLE: Parallelization
STATEMENT: Saturn shall enable parallelization of the time-consuming parts of the code.

[REQUIREMENT]
UID: SDOC-IMPL-INCREMENTAL
TITLE: Incremental generation
STATEMENT: Saturn shall enable incremental generation of the documents.

[/SECTION]

[SECTION]
LEVEL: 1
TITLE: Data model

[REQUIREMENT]
UID: SDOC-DM-001
REFS:
- TYPE: Parent
  VALUE: SDOC-HIGH-REQS-MANAGEMENT
TITLE: Modeling capability
STATEMENT: Saturn's Data Model shall accommodate for maximum possible standard requirement document formats.
BODY: >>>
Examples of standard requirements documents include but are not limited to:

- Non-nested requirement lists split by categories
  (e.g., Functional Requirements, Interface Requirements, Performance Requirements, etc.)
<<<

[SECTION]
LEVEL: 2
TITLE: Section item

[/SECTION]

[SECTION]
LEVEL: 2
TITLE: Requirement item

[REQUIREMENT]
TITLE: Statement
STATEMENT: Requirement item shall have a statement.

[REQUIREMENT]
TITLE: Content body
STATEMENT: Requirement item might have an content body.

[COMPOSITE-REQUIREMENT]
TITLE: UID identifier
STATEMENT: Requirement item might have an UID identifier.

[REQUIREMENT]
TITLE: UID identifier format
STATEMENT: Saturn shall not impose any restrictions on the UID field format.
COMMENT: >>>
Conventions used for requirement UIDs can be very different. And there seems to
be no way to define a single rule.

Some examples:

- FUN-003
- cES1008, cTBL6000.1 (NASA cFS)
- Requirements without a number, e.g. SDOC-HIGH-DATA-MODEL (Saturn)
<<<

[/COMPOSITE-REQUIREMENT]

[REQUIREMENT]
TITLE: Title
STATEMENT: Requirement item might have an title.

[REQUIREMENT]
TITLE: References
STATEMENT: Requirement item might have one or more references.

[REQUIREMENT]
TITLE: Comments
STATEMENT: Requirement item might have one or more comments.

[/SECTION]

[SECTION]
LEVEL: 2
TITLE: Composite Requirement item

[FREETEXT]
TBD
[/FREETEXT]

[/SECTION]

[/SECTION]

[SECTION]
LEVEL: 1
TITLE: SDOC file format

[REQUIREMENT]
UID: SDOC-RDF-001
REFS:
- TYPE: Parent
  VALUE: SDOC-DM-001
TITLE: Primary text implementation
STATEMENT: SDOC format shall support encoding the Strict Doc Data Model in a plain-text human readable form.

[REQUIREMENT]
TITLE: Grammar
STATEMENT: SDOC format shall be based on a fixed grammar.

[REQUIREMENT]
TITLE: Type safety
STATEMENT: SDOC format shall allow type-safe encoding of requirement documents.

[/SECTION]

[SECTION]
LEVEL: 1
TITLE: Document Generators

[SECTION]
LEVEL: 2
TITLE: HTML Export

[REQUIREMENT]
TITLE: Single document: Normal form
STATEMENT: Saturn shall export single document pages in a normal document-like form.

[REQUIREMENT]
TITLE: Single document: Tabular form
STATEMENT: Saturn shall export single document pages in a tabular form.

[REQUIREMENT]
REFS:
- TYPE: Parent
  VALUE: SDOC-HIGH-REQS-TRACEABILITY
TITLE: Single document: 1-level traceability
STATEMENT: Saturn shall export 1-level traceability document.

[REQUIREMENT]
REFS:
- TYPE: Parent
  VALUE: SDOC-HIGH-REQS-TRACEABILITY
TITLE: Single document: Deep traceability
STATEMENT: Saturn shall export deep traceability document.

[/SECTION]

[SECTION]
LEVEL: 2
TITLE: PDF Export

[REQUIREMENT]
TITLE: Sphinx documentation generator
STATEMENT: Saturn shall support exporting documents to Sphinx/RST format.

[/SECTION]

[/SECTION]
