[DOCUMENT]
TITLE: Test Document
OPTIONS:
  REQUIREMENT_STYLE: Inline
  DEFAULT_VIEW: VIEW_THAT_DOES_NOT_EXIST
VIEWS:
- ID: FIELD_VIEW
  NAME: Field view
  TAGS:
  - OBJECT_TYPE: REQUIREMENT
    VISIBLE_FIELDS:
    - NAME: UID
      PLACEMENT: XYZ
    - NAME: STATEMENT
