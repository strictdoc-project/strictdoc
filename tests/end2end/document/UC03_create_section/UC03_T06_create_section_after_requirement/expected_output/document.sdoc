[DOCUMENT]
TITLE: Document 1

[FREETEXT]
Hello world!
[/FREETEXT]

[REQUIREMENT]
TITLE: Requirement title
STATEMENT: >>>
Requirement statement.
<<<

[SECTION]
TITLE: Section title

[FREETEXT]
Section statement.
[/FREETEXT]

[/SECTION]
