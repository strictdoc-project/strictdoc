[DOCUMENT]
TITLE: Test document

[GRAMMAR]
ELEMENTS:
- TAG: REQUIREMENT
  FIELDS:
  - TITLE: UID
    TYPE: String
    REQUIRED: False
  - TITLE: STATEMENT
    TYPE: String
    REQUIRED: False
  - TITLE: ASIL
    TYPE: String
    REQUIRED: False
  - TITLE: STATUS
    TYPE: String
    REQUIRED: False
  - TITLE: COMMENT
    TYPE: String
    REQUIRED: False

[REQUIREMENT]
UID: ABC-123
STATEMENT: >>>
Requirement 7.8.9
<<<
ASIL: A
STATUS: Draft
COMMENT: >>>
Test comment.
<<<
