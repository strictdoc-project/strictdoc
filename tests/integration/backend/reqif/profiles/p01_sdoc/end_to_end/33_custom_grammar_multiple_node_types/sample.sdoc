[DOCUMENT]
TITLE: sample

[GRAMMAR]
ELEMENTS:
- TAG: TEXT
  FIELDS:
  - TITLE: UID
    TYPE: String
    REQUIRED: False
  - TITLE: STATEMENT
    TYPE: String
    REQUIRED: False
  RELATIONS:
  - TYPE: Parent
  - TYPE: File
- TAG: REQUIREMENT
  FIELDS:
  - TITLE: UID
    TYPE: String
    REQUIRED: False
  - TITLE: STATEMENT
    TYPE: String
    REQUIRED: False
  - TITLE: ASIL
    TYPE: String
    REQUIRED: False
  - TITLE: STATUS
    TYPE: String
    REQUIRED: False
  - TITLE: COMMENT
    TYPE: String
    REQUIRED: False
  RELATIONS:
  - TYPE: Parent
  - TYPE: File
- TAG: ASSUMPTION
  FIELDS:
  - TITLE: UID
    TYPE: String
    REQUIRED: False
  - TITLE: TITLE
    TYPE: String
    REQUIRED: False
  - TITLE: STATEMENT
    TYPE: String
    REQUIRED: False
  - TITLE: COMMENT
    TYPE: String
    REQUIRED: False
  RELATIONS:
  - TYPE: Parent
  - TYPE: File

[TEXT]
STATEMENT: >>>
Document free text.
<<<

[SECTION]
TITLE: Section 1

[TEXT]
STATEMENT: >>>
Section 1 free text.
<<<

[REQUIREMENT]
UID: REQ-1
STATEMENT: >>>
Requirement 1 statement.
<<<
ASIL: A
STATUS: Draft
COMMENT: >>>
Test comment.
<<<

[ASSUMPTION]
UID: ASSUMPTION-1
TITLE: Assumption 1 Title
STATEMENT: >>>
Assumption 1 statement.
<<<

[/SECTION]
