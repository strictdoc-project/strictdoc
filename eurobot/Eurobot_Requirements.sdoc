[DOCUMENT]
TITLE: Системные требования

[GRAMMAR]
IMPORT_FROM_FILE: @eurobot_requirements

[TEXT]
STATEMENT: >>>
Системные требования («чёрный ящик»). Каждое требование объявляет отношение
``COVERS`` к каждому правилу (``RULE``), которое оно затрагивает.

Эти четыре требования покрывают три пункта из 93, которые содержит
``Eurobot_Rules.sdoc``, поэтому Матрица трассируемости показывает длинный
список правил, для которых требование ещё не написано. Сократить этот
список — задача самого курса.

Правила приведены на русском языке, требования — тоже: правила дословно
цитируются из документов соревнования, а требования — собственный текст
курса, написанный (и переведённый) на русском, поскольку студенты курса
говорят по-русски.
<<<

[[SECTION]]
TITLE: Входы

[INTERFACE_PARAMETER]
TITLE: input.started_cord
STATEMENT: >>>
Описание: Стартовый корд

Тип: bool

Значения:

* false значит вставлен
* true значит извлечен
<<<

[[/SECTION]]

[[SECTION]]
TITLE: Выходы

[INTERFACE_PARAMETER]
TITLE: cmd.velocity.x
STATEMENT: >>>
Описание: Команда движения робота

Тип: float
<<<

[[/SECTION]]

[[SECTION]]
TITLE: Конфигурационные параметры

[INTERFACE_PARAMETER]
TITLE: cfg.ref_velocity
STATEMENT: >>>
Тип: float

Значение: 70

Единицы измерения: проценты
<<<

[[/SECTION]]

[[SECTION]]
TITLE: Отладочные выходы

[INTERFACE_PARAMETER]
TITLE: dbg.pose.position.x
STATEMENT: >>>
Описание: Текущая позиция робота по оси X

Тип: float
<<<

[INTERFACE_PARAMETER]
TITLE: dbg.pose.position.y
STATEMENT: >>>
Описание: Текущая позиция робота по оси Y

Тип: float
<<<

[INTERFACE_PARAMETER]
TITLE: dbg.pose.orientation.yaw
STATEMENT: >>>
Описание: Текущая ориентация робота вокруг оси Z

Тип: float
<<<

[[/SECTION]]

[[SECTION]]
TITLE: Функциональные требования

[REQUIREMENT]
UID: REQ-6
TITLE: Движение при извлечении корда
TARGET_REVISION: TBD
STATEMENT: >>>
ЕСЛИ стартовый корд выдернут (input.started_cord==true)

ТО робот должен начать движение вперед (cmd.velocity.x = cfg.ref_velocity)
<<<
RELATIONS:
- TYPE: Parent
  VALUE: RULE-GENERAL-I.3.b
  ROLE: COVERS

[REQUIREMENT]
UID: REQ-3
TITLE: Аварийная остановка обесточивает приводы
TARGET_REVISION: C2
STATEMENT: >>>
Нажатие кнопки аварийной остановки должно снимать питание со всех двигателей
и приводов в течение 100 мс, и робот должен оставаться обесточенным до
отпускания кнопки.

Кнопка должна располагаться на верхней части робота или на стороне,
доступной судье без необходимости что-либо передвигать.
<<<
RELATIONS:
- TYPE: Parent
  VALUE: RULE-GENERAL-F.4.c
  ROLE: COVERS

[[/SECTION]]

[REQUIREMENT]
UID: REQ-1
TITLE: Периметр в начале матча
TARGET_REVISION: C1
STATEMENT: >>>
В начале матча робот должен помещаться в периметр не более 1200 мм,
измеренный по выпуклой оболочке его вертикальной проекции на землю.
<<<
RELATIONS:
- TYPE: Parent
  VALUE: RULE-GENERAL-F.3
  ROLE: COVERS

[REQUIREMENT]
UID: REQ-2
TITLE: Высота во время матча
TARGET_REVISION: C1
STATEMENT: >>>
В любой момент матча высота робота от поверхности стола до его самой
высокой точки должна быть не более 350 мм. Мачта крепления маяка, а также
датчики и схемы, установленные под ней, в этот замер не входят.
<<<
RELATIONS:
- TYPE: Parent
  VALUE: RULE-GENERAL-F.3
  ROLE: COVERS

[REQUIREMENT]
UID: REQ-4
TITLE: Автономный цикл матча
TARGET_REVISION: TBD
STATEMENT: >>>
После стартового сигнала судьи робот должен выполнять свою стратегию матча
в течение 100 секунд и полностью остановить любое движение по истечении
этого времени. Во время матча он не должен принимать никаких команд от
команды.
<<<
RELATIONS:
- TYPE: Parent
  VALUE: RULE-GENERAL-H.2
  ROLE: COVERS
