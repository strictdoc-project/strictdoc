[DOCUMENT]
TITLE: Document with a requirement with two comments.
OPTIONS:
  MARKUP: HTML

[GRAMMAR]
ELEMENTS:
- TAG: REQUIREMENT
  FIELDS:
  - TITLE: UID
    TYPE: String
    REQUIRED: False
  - TITLE: LEVEL
    TYPE: String
    REQUIRED: False
  - TITLE: STATUS
    TYPE: String
    REQUIRED: False
  - TITLE: TAGS
    TYPE: String
    REQUIRED: False
  - TITLE: TITLE
    TYPE: String
    REQUIRED: False
  - TITLE: STATEMENT
    TYPE: String
    REQUIRED: False
  - TITLE: RATIONALE
    TYPE: String
    REQUIRED: False
  - TITLE: COMMENT
    TYPE: String
    REQUIRED: False
  RELATIONS:
  - TYPE: Parent
  - TYPE: File

[SECTION]
TITLE: Section #1

[REQUIREMENT]
UID: REQ-001
TITLE: Requirement #1

[REQUIREMENT]
UID: REQ-002
TITLE: Requirement #2
RELATIONS:
- TYPE: Parent
  VALUE: REQ-001

[/SECTION]
