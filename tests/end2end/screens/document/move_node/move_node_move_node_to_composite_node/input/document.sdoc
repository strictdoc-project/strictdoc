[DOCUMENT]
TITLE: Document 1

[TEXT]
STATEMENT: >>>
Hello world!
<<<

[[SECTION]]
TITLE: Section title #1

[TEXT]
STATEMENT: >>>
NOT_RELEVANT
<<<

[[/SECTION]]

[[SECTION]]
TITLE: Section title #2

[TEXT]
STATEMENT: >>>
NOT_RELEVANT
<<<

[[SECTION]]
TITLE: Section title #2.1

[TEXT]
STATEMENT: >>>
NOT_RELEVANT
<<<

[[/SECTION]]

[[SECTION]]
TITLE: Section title #2.2

[TEXT]
STATEMENT: >>>
NOT_RELEVANT
<<<

[[/SECTION]]

[[/SECTION]]
