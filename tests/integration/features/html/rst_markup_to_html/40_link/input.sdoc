[DOCUMENT]
TITLE: Links

[TEXT]
STATEMENT: >>>
[ANCHOR: THING-1, Thing]
Something.
<<<

[TEXT]
STATEMENT: >>>
[LINK: THING-1] may be followed by whitespace.
[LINK: THING-1]	may be followed by tab.
Maybe punctuation like comma follows [LINK: THING-1], or dot follows [LINK: THING-1].
[LINK: THING-1]s may be followed by character.
<<<
