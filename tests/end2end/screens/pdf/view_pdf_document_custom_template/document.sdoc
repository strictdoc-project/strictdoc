[DOCUMENT]
TITLE: Empty Document
VERSION: Git commit: @GIT_VERSION, Git branch: @GIT_BRANCH
DATE: @GIT_COMMIT_DATETIME
CLASSIFICATION: Confidential
OPTIONS:
  VIEW_STYLE: Inline
METADATA:
  AUTHOR: James T. Kirk
  CHECKED-BY: Chuck Norris
  APPROVED-BY: Wile E. Coyote
