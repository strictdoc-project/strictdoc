[DOCUMENT]
MID: d3457617ba0544beaccf913f547cd6dc
TITLE: File In Subfolder
OPTIONS:
  ENABLE_MID: True

[GRAMMAR]
IMPORT_FROM_FILE: @my_grammar

[REQUIREMENT]
MID: 46355ead6a8b4974b134b200eec4a885
UID: SUB-ROOT-1
TITLE: Requirement in root
STATEMENT: >>>
lorem ipsum
<<<

[[SECTION]]
MID: ca56014cd79345a8bb098b757ea6f0c9
TITLE: Section without UID containing a requirement

[REQUIREMENT]
MID: 9281cd61e9954ce68ec54f95bdc7f687
UID: SUB-REQ-WITHIN-SECTION-THAT-HAS-NO-UID
TITLE: Requirment within a Section
STATEMENT: lorem ipsum

[[/SECTION]]

[[SECTION]]
MID: 49def62923244e118129a4888ff0ace7
UID: SUB-SECTION-1
TITLE: Section that has an UID

[TEXT]
STATEMENT: lorem ipsum

[[/SECTION]]

[[SECTION]]
MID: 0a9eee57cac44286ad3dc828687aa23e
UID: SUB-SECTION-2
TITLE: Section with UID containing a requirement

[REQUIREMENT]
MID: c1b59b53ef144d8981ce2b5e1c7ca315
UID: SUB-REQ-WITHIN-SECTION-2
TITLE: Requirement within a Section that has a UID
STATEMENT: lorem ipsum

[[/SECTION]]

[[SECTION]]
MID: 29718f836810479bb2f73b52df4c8968
UID: SUB-SECTION-3
TITLE: Nested Sections Test

[[SECTION]]
MID: 320bba79bded44528ccddd6c8c8ff08e
UID: SUB-SECTION-3-1
TITLE: Subsection for the nexted section test

[REQUIREMENT]
MID: 20459e2510ac41c5b79d4c18149fc1b1
UID: SUB-REQ-WITHIN-SECTION-3-1
TITLE: Requirement within a nested Section
STATEMENT: lorem ipsum

[[/SECTION]]

[[/SECTION]]
