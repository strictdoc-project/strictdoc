[DOCUMENT]
MID: 6a8bc1d467c348dbad29707cd6a3f261
TITLE: Specification Graph Screen Test
OPTIONS:
  ENABLE_MID: True

[[SECTION]]
MID: sect-2345
TITLE: Test section

[REQUIREMENT]
MID: req-2345
UID: REQ-1
TITLE: Sample requirement
STATEMENT: >>>
A sample requirement used to exercise the Specification Graph screen.
<<<

[[/SECTION]]
