[DOCUMENT]
NAME: StrictDoc Roadmap

[SECTION]
LEVEL: 1
TITLE: In works

[SECTION]
LEVEL: 2
TITLE: CSS Work

[REQUIREMENT]
TITLE: Document page CSS: Proper markup
STATEMENT: Document page: make it look like a document.

[REQUIREMENT]
TITLE: Table page CSS: Proper table
STATEMENT: Table page: make columns be always of the same size while respecting min-max widths.

[REQUIREMENT]
TITLE: Traceability page CSS: Proper middle column document
STATEMENT: Traceability page CSS: Proper middle column document

[REQUIREMENT]
TITLE: Deep Traceability page CSS: Improvements
STATEMENT: Deep Traceability page CSS: Improvements

[/SECTION]

[/SECTION]

[SECTION]
LEVEL: 1
TITLE: Roadmap

[REQUIREMENT]
TITLE: Platform support
STATEMENT: StrictDoc shall work on macOS, Linux, and Windows systems.

[REQUIREMENT]
TITLE: Custom fields
STATEMENT: StrictDoc shall support customization of the default grammar with custom fields.
COMMENT: Examples: RAIT compliance fields, ASIL level.

[REQUIREMENT]
TITLE: Filtering by tags
STATEMENT: StrictDoc shall support filtering filtering by tags.

[REQUIREMENT]
TITLE: Generated file names
STATEMENT: Document name must be transformed into a valid file name.

[REQUIREMENT]
TITLE: Linking with implementation artifacts
STATEMENT: StrictDoc shall support linking requirements to files.

[REQUIREMENT]
TITLE: Documentation coverage
STATEMENT: StrictDoc shall generate requirements coverage information.

[REQUIREMENT]
TITLE: Graphical User Interface (GUI)
STATEMENT: StrictDoc shall provide a Graphical User Interface (GUI).

[REQUIREMENT]
TITLE: Validation: Section Levels
STATEMENT: Section levels must be nested.

[REQUIREMENT]
TITLE: Option: Title: Automatic numeration
STATEMENT: StrictDoc shall support config option `numeric_titles`.

[REQUIREMENT]
TITLE: Option: Title: Display requirement titles
STATEMENT: StrictDoc shall support config option `display_requirement_titles`.

[REQUIREMENT]
TITLE: Option: Title: Display requirement UID
STATEMENT: StrictDoc shall support config option `display_requirement_uids`.

[REQUIREMENT]
TITLE: Advanced: Extraction of numeric values into separate table. Invariants calculation.
STATEMENT: StrictDoc shall support calculating invariants that enforce numerical constraints.

[/SECTION]
