[DOCUMENT]
TITLE: Hello world doc

[REQUIREMENT]
UID: REQ-1
TITLE: Requirement Title #1
STATEMENT: Requirement Statement
RELATIONS:
- TYPE: File
  VALUE: file.py
  FUNCTION: hello_world

[REQUIREMENT]
UID: REQ-2
TITLE: Requirement Title #2
STATEMENT: Requirement Statement
RELATIONS:
- TYPE: File
  VALUE: file.py
  FUNCTION: hello_world
