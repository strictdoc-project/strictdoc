[DOCUMENT]
TITLE: Document 1

[FREETEXT]
Hello world!
[/FREETEXT]

[SECTION]
UID: AD1
TITLE: First section

[FREETEXT]
This is a free text of this section.
[/FREETEXT]

[/SECTION]

[SECTION]
TITLE: Section with LINK

[FREETEXT]
Statement with LINK:

[LINK: AD1]
[/FREETEXT]

[/SECTION]
