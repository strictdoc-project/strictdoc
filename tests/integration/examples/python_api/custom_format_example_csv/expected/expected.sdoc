[DOCUMENT]
TITLE: CSV Example

[[SECTION]]
TITLE: Section 1

[REQUIREMENT]
UID: REQ-1
TITLE: Requirement 1
STATEMENT: >>>
Statement for requirement 1.
<<<

[REQUIREMENT]
UID: REQ-2
TITLE: Requirement 2
STATEMENT: >>>
Statement for requirement 2.
<<<

[REQUIREMENT]
UID: REQ-3
TITLE: Requirement 3
STATEMENT: >>>
Statement for requirement 3.
<<<

[[/SECTION]]

[[SECTION]]
TITLE: Section 2

[REQUIREMENT]
UID: REQ-4
TITLE: Requirement 4
STATEMENT: >>>
Statement for requirement 4.
<<<

[REQUIREMENT]
UID: REQ-5
TITLE: Requirement 5
STATEMENT: >>>
Statement for requirement 5.
<<<

[REQUIREMENT]
UID: REQ-6
TITLE: Requirement 6
STATEMENT: >>>
Statement for requirement 6.
<<<

[[/SECTION]]
