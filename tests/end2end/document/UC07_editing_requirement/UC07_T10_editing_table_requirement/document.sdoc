[DOCUMENT]
TITLE: Document 1
OPTIONS:
  REQUIREMENT_STYLE: Table

[FREETEXT]
Hello world!
[/FREETEXT]

[REQUIREMENT]
TITLE: Requirement title
STATEMENT: >>>
Requirement statement.
<<<
RATIONALE: >>>
Requirement rationale.
<<<
