[DOCUMENT]
TITLE: Document title

[[SECTION]]
TITLE: Section without UID

[[/SECTION]]

[[SECTION]]
UID: SECTION_01
TITLE: Section with UID

[[/SECTION]]

[REQUIREMENT]
UID: REQ_01
STATEMENT: >>>
It has not a title and doesn't go in the TOC.
<<<

[REQUIREMENT]
UID: REQ_02
TITLE: Requirement 2 title
STATEMENT: >>>
Requirement statement.
<<<

[[SECTION]]
UID: SECTION_PARENT
TITLE: Parent section

[[SECTION]]
UID: SECTION_CHILD
TITLE: Child section

[[SECTION]]
UID: SECTION_GRANDCHILD
TITLE: Grandchild section

[[/SECTION]]

[[/SECTION]]

[[/SECTION]]
