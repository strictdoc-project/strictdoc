[DOCUMENT]
TITLE: Document 1

[FREETEXT]
Hello world!
[/FREETEXT]

[SECTION]
TITLE: Section title

[FREETEXT]
Section text.
[/FREETEXT]

[/SECTION]

[REQUIREMENT]
TITLE: Requirement title
STATEMENT: >>>
Requirement statement.
<<<
