[DOCUMENT]
TITLE: Document 1
REQ_PREFIX: ZEP-

[FREETEXT]
Hello world!
[/FREETEXT]

[REQUIREMENT]
UID: ZEP-2
TITLE: Requirement title #2.1
STATEMENT: >>>
Requirement statement #2.1.
<<<
RATIONALE: >>>
Requirement rationale #2.1.
<<<
