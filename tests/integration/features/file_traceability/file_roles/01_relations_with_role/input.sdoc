[DOCUMENT]
TITLE: Hello world doc

[GRAMMAR]
ELEMENTS:
- TAG: REQUIREMENT
  FIELDS:
  - TITLE: MID
    TYPE: String
    REQUIRED: False
  - TITLE: UID
    TYPE: String
    REQUIRED: False
  - TITLE: TITLE
    TYPE: String
    REQUIRED: False
  - TITLE: STATEMENT
    TYPE: String
    REQUIRED: False
  RELATIONS:
  - TYPE: File
    ROLE: Implementation
  - TYPE: File
    ROLE: Test
  - TYPE: File

[REQUIREMENT]
UID: REQ-001
TITLE: Requirement Title 1
STATEMENT: >>>
Requirement with reverse relations from files.
<<<
