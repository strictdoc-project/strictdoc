[DOCUMENT]
TITLE: Doc with a requirement that have no title

[REQUIREMENT]
UID: REQ1
TITLE: Requirement 1
STATEMENT: >>>
System shall do #1.
<<<
COMMENT: >>>
Requirement 1 comment.
<<<

[REQUIREMENT]
UID: REQ2
TITLE: Requirement 2
STATEMENT: >>>
System shall do #2.
<<<
COMMENT: >>>
Requirement 2 comment.
<<<
