[DOCUMENT]
TITLE: Document One

[REQUIREMENT]
UID: REQ-002
TITLE: Parent requirement
STATEMENT: The system shall do the parent thing.

[REQUIREMENT]
UID: REQ-001
TITLE: Child requirement
STATEMENT: The system shall do the child thing.
RELATIONS:
- TYPE: Parent
  VALUE: REQ-002
