[DOCUMENT]
TITLE: Hello world doc
OPTIONS:
  AUTO_LEVELS: Off

[SECTION]
LEVEL: 1.2.3
TITLE: Section 1.2.3

[COMPOSITE_REQUIREMENT]
STATEMENT: Composite requirement 4.5.6

[REQUIREMENT]
LEVEL: 7.8.9
STATEMENT: Requirement 7.8.9

[/COMPOSITE_REQUIREMENT]

[/SECTION]
