[DOCUMENT]
TITLE: Hello world doc

[REQUIREMENT]
UID: REQ-AUTH-001
TITLE: UI Login
STATEMENT: The system shall provide a dialog to authenticate users.

[REQUIREMENT]
UID: REQ-AUTH-002
TITLE: UI Login
STATEMENT: Login attempts with invalid credentials shall be rejected with error message and redirect to an empty login dialog.
