[DOCUMENT]
TITLE: Document 1

[FREETEXT]
Hello world!
[/FREETEXT]

[REQUIREMENT]
STATEMENT: >>>
Requirement statement.
<<<
COMMENT: >>>
Comment #1
<<<
COMMENT: >>>
Comment #2
<<<
COMMENT: >>>
Comment #3
<<<
