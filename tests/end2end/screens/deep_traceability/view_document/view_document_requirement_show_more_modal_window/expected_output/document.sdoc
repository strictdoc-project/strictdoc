[DOCUMENT]
TITLE: Document title
OPTIONS:
  VIEW_STYLE: Table

[[SECTION]]
UID: SEC_UID
TITLE: Section title

[REQUIREMENT]
UID: REC_UID
TITLE: Requirement title
STATEMENT: >>>
Requirement statement.
<<<
RATIONALE: >>>
Requirement rationale.
<<<

[[/SECTION]]
