[DOCUMENT]
TITLE: Doc 1

[GRAMMAR]
ELEMENTS:
- TAG: REQUIREMENT
  FIELDS:
  - TITLE: UID
    TYPE: String
    REQUIRED: True
  - TITLE: STATEMENT
    TYPE: String
    REQUIRED: True
  RELATIONS:
  - TYPE: Child

[REQUIREMENT]
UID: REQ-001
STATEMENT: Hello world 1
RELATIONS:
- TYPE: Child
  VALUE: REQ-002

[REQUIREMENT]
UID: REQ-002
STATEMENT: Hello world 2
RELATIONS:
- TYPE: Child
  VALUE: REQ-001
