[DOCUMENT]
TITLE: Document 1

[FREETEXT]
Hello world!
[/FREETEXT]

[SECTION]
TITLE: First title

[FREETEXT]
This is a free text of the first section.

[ANCHOR: AD1]
[/FREETEXT]

[/SECTION]

[SECTION]
TITLE: Second title

[FREETEXT]
This is a free text of the second section.

[LINK: AD1]
[/FREETEXT]

[/SECTION]
