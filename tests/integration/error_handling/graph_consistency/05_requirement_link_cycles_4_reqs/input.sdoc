[DOCUMENT]
TITLE: Doc 1

[REQUIREMENT]
UID: REQ-001
STATEMENT: Hello world 1
RELATIONS:
- TYPE: Parent
  VALUE: REQ-004

[REQUIREMENT]
UID: REQ-002
STATEMENT: Hello world 2
RELATIONS:
- TYPE: Parent
  VALUE: REQ-001

[REQUIREMENT]
UID: REQ-003
STATEMENT: Hello world 3
RELATIONS:
- TYPE: Parent
  VALUE: REQ-002

[REQUIREMENT]
UID: REQ-004
STATEMENT: Hello world 4
RELATIONS:
- TYPE: Parent
  VALUE: REQ-003
