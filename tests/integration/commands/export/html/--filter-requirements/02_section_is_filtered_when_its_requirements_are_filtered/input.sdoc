[DOCUMENT]
TITLE: Hello world doc

[REQUIREMENT]
TITLE: Title #1
STATEMENT: Statement #1

[REQUIREMENT]
TITLE: Title #2
STATEMENT: Statement #2

[SECTION]
TITLE: MUST_BE_FILTERED

[REQUIREMENT]
TITLE: Title #3
STATEMENT: Statement #3

[REQUIREMENT]
TITLE: Title #4
STATEMENT: Statement #4

[/SECTION]
