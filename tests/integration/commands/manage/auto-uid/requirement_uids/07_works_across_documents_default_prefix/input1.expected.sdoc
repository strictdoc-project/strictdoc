[DOCUMENT]
TITLE: Hello world doc 1

[REQUIREMENT]
UID: REQ-1
STATEMENT: System 1 shall do 1.

[REQUIREMENT]
UID: REQ-2
STATEMENT: System 1 shall do 2.

[REQUIREMENT]
UID: REQ-3
STATEMENT: System 1 shall do 3.
