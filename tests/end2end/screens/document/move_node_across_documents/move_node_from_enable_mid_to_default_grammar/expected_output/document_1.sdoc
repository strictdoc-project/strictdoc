[DOCUMENT]
MID: 11111111111111111111111111111111
TITLE: MID Document
OPTIONS:
  ENABLE_MID: True

[GRAMMAR]
ELEMENTS:
- TAG: SECTION
  PROPERTIES:
    IS_COMPOSITE: True
    PREFIX: None
    VIEW_STYLE: Narrative
  FIELDS:
  - TITLE: MID
    TYPE: String
    REQUIRED: False
  - TITLE: UID
    TYPE: String
    REQUIRED: False
  - TITLE: TITLE
    TYPE: String
    REQUIRED: True
- TAG: TEXT
  PROPERTIES:
    VIEW_STYLE: Narrative
  FIELDS:
  - TITLE: MID
    TYPE: String
    REQUIRED: True
  - TITLE: STATEMENT
    TYPE: String
    REQUIRED: True
  RELATIONS:
  - TYPE: Parent
  - TYPE: File

[[SECTION]]
MID: 22222222222222222222222222222222
TITLE: Moved section

[TEXT]
MID: 33333333333333333333333333333333
STATEMENT: >>>
Text moved from an ENABLE_MID document.
<<<

[[/SECTION]]
