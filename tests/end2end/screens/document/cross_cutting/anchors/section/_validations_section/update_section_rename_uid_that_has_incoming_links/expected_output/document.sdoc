[DOCUMENT]
TITLE: Document 1

[FREETEXT]
Hello world!
[/FREETEXT]

[SECTION]
UID: Section-UID
TITLE: First section

[FREETEXT]
This is a free text of this section.
[/FREETEXT]

[/SECTION]

[SECTION]
TITLE: Second section

[FREETEXT]
This is a free text of this section.

[LINK: Section-UID]
[/FREETEXT]

[/SECTION]

[SECTION]
TITLE: Third section

[FREETEXT]
This is a free text of this section.

[LINK: Section-UID]
[/FREETEXT]

[/SECTION]
