[DOCUMENT]
TITLE: Document 2

[GRAMMAR]
ELEMENTS:
- TAG: SECTION
  PROPERTIES:
    IS_COMPOSITE: True
  FIELDS:
  - TITLE: UID
    TYPE: String
    REQUIRED: False
  - TITLE: LEVEL
    TYPE: String
    REQUIRED: False
  - TITLE: PREFIX
    TYPE: String
    REQUIRED: False
  - TITLE: TITLE
    TYPE: String
    REQUIRED: False
- TAG: TEXT
  FIELDS:
  - TITLE: STATEMENT
    TYPE: String
    REQUIRED: False

[TEXT]
STATEMENT: >>>
Document 2 free text.
<<<

[[SECTION]]
TITLE: Document 2 section

[TEXT]
STATEMENT: >>>
Document 2 statement.
<<<

[[/SECTION]]
