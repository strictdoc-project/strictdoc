[DOCUMENT]
TITLE: Dummy Software Requirements Specification #1

[TEXT]
STATEMENT: >>>
.. image:: _assets/file.svg
   :alt: Test image
   :class: image
   :width: 100%
<<<

[DOCUMENT_FROM_FILE]
FILE: nested/input2.sdoc
