[DOCUMENT]
TITLE: Document 1

[REQUIREMENT]
UID: REQ-001
TITLE: Requirement to keep
STATEMENT: >>>
Keep this requirement.
<<<

[[SECTION]]
TITLE: Section to delete

[TEXT]
STATEMENT: >>>
Delete this section.
<<<

[[/SECTION]]
