[DOCUMENT]
TITLE: Empty ReqIF document
OPTIONS:
  MARKUP: Text

[REQUIREMENT]
UID: REQ-001
STATEMENT: Requirement 1 statement.

[REQUIREMENT]
UID: REQ-002
REFS:
- TYPE: Parent
  VALUE: REQ-001
STATEMENT: Requirement 2 statement.
