[DOCUMENT]
TITLE: Low-Level Requirements Document
PREFIX: SDD-LLR-

[GRAMMAR]
ELEMENTS:
- TAG: TEXT
  FIELDS:
  - TITLE: UID
    TYPE: String
    REQUIRED: False
  - TITLE: STATEMENT
    TYPE: String
    REQUIRED: True
- TAG: REQUIREMENT
  PROPERTIES:
    PREFIX: REQ-
  FIELDS:
  - TITLE: MID
    TYPE: String
    REQUIRED: False
  - TITLE: UID
    TYPE: String
    REQUIRED: False
  - TITLE: STATEMENT
    TYPE: String
    REQUIRED: False
- TAG: DEFINITION
  PROPERTIES:
    PREFIX: DEF-
  FIELDS:
  - TITLE: MID
    TYPE: String
    REQUIRED: False
  - TITLE: UID
    TYPE: String
    REQUIRED: False
  - TITLE: STATEMENT
    TYPE: String
    REQUIRED: False

[REQUIREMENT]
STATEMENT: System 2 shall do 1.

[DEFINITION]
STATEMENT: Definition 2.
