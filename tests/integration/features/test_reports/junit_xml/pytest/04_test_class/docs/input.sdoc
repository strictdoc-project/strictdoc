[DOCUMENT]
TITLE: Hello world doc

[REQUIREMENT]
UID: REQ-1
STATEMENT: Test statement 1.

[REQUIREMENT]
UID: REQ-2
STATEMENT: Test statement 2.

[REQUIREMENT]
UID: REQ-3
STATEMENT: Test statement 3.

[REQUIREMENT]
UID: REQ-4
STATEMENT: Test statement 4.
