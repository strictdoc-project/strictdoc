[DOCUMENT]
MID: 398e37d756ea406f87ca83ec8e29c178
TITLE: Document 1
OPTIONS:
  ENABLE_MID: True

[REQUIREMENT]
MID: a5c6b14d5ee443149687fb9be69a7ede
STATEMENT: >>>
Before image.

.. image:: ./_assets/a5c6b14d5ee443149687fb9be69a7ede/picture.svg

Drop the second file here.
<<<
RATIONALE: >>>
Keep this reference unchanged:

.. image:: ./_assets/a5c6b14d5ee443149687fb9be69a7ede/picture.svg

Insert the unreferenced pair here.
<<<
