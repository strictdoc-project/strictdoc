[DOCUMENT]
TITLE: Hello world doc

[REQUIREMENT]
UID: REQ-1
STATEMENT: Shall do 1.

[REQUIREMENT]
UID: REQ-2
STATEMENT: Shall do 1.
REFS:
- TYPE: Parent
  VALUE: REQ-1

[REQUIREMENT]
UID: REQ-3
STATEMENT: Shall do 1.
RELATIONS:
- TYPE: Parent
  VALUE: REQ-1
