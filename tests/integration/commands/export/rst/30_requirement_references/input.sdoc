[DOCUMENT]
TITLE: Doc with a requirement that have no title

[REQUIREMENT]
UID: REQ1
TITLE: Requirement 1
STATEMENT: >>>
System shall do #1.
<<<
COMMENT: >>>
Requirement 1 comment.
<<<

[REQUIREMENT]
UID: REQ2
TITLE: Requirement 2
STATEMENT: >>>
System shall do #2.
<<<
COMMENT: >>>
Requirement 2 comment.
<<<
RELATIONS:
- TYPE: Parent
  VALUE: REQ1

[REQUIREMENT]
UID: REQ3
TITLE: Requirement 3
STATEMENT: >>>
System shall do #3.
<<<
COMMENT: >>>
Requirement 3 comment.
<<<
RELATIONS:
- TYPE: Parent
  VALUE: REQ1
- TYPE: Parent
  VALUE: REQ2
