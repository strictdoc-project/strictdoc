[DOCUMENT]
TITLE: Test document

[GRAMMAR]
ELEMENTS:
- TAG: REQUIREMENT
  FIELDS:
  - TITLE: UID
    TYPE: String
    REQUIRED: True
  - TITLE: STATEMENT
    TYPE: String
    REQUIRED: True

[UNKNOWN_REQUIREMENT]
UID: ABC-123
