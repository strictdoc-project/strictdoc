[DOCUMENT]
TITLE: Document 1

[GRAMMAR]
ELEMENTS:
- TAG: TEXT
  FIELDS:
  - TITLE: UID
    TYPE: String
    REQUIRED: False
  - TITLE: STATEMENT
    TYPE: String
    REQUIRED: True
- TAG: REQUIREMENT
  FIELDS:
  - TITLE: UID
    TYPE: String
    REQUIRED: False
  - TITLE: LEVEL
    TYPE: String
    REQUIRED: False
  - TITLE: TAGS
    TYPE: Tag
    REQUIRED: False
  - TITLE: TITLE
    TYPE: String
    REQUIRED: False
  - TITLE: STATEMENT
    TYPE: String
    REQUIRED: False
  - TITLE: RATIONALE
    TYPE: String
    REQUIRED: False
  - TITLE: COMMENT
    TYPE: String
    REQUIRED: False
  RELATIONS:
  - TYPE: Parent
  - TYPE: File

[REQUIREMENT]
UID: REQ-1
TAGS: Tag1
TITLE: Requirement 1 ABC
STATEMENT: >>>
Shall test foo.
<<<

[REQUIREMENT]
UID: REQ-2
TAGS: Tag2
TITLE: Requirement 2 XYZ
STATEMENT: >>>
Shall test bar.
<<<

[REQUIREMENT]
UID: REQ-3
TAGS: Tag1, Tag2
TITLE: New Requirement
STATEMENT: >>>
Shall test foo 2.
<<<
