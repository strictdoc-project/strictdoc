[DOCUMENT]
TITLE: Document 1

[[SECTION]]
UID: AD1
TITLE: First section

[[/SECTION]]

[[SECTION]]
TITLE: Second section

[REQUIREMENT]
STATEMENT: >>>
Statement with LINK: [LINK: AD1]
<<<

[[/SECTION]]
