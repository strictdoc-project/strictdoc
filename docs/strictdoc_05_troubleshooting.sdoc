[DOCUMENT]
MID: 5680165c90f44903b3b1dc1013b8cb59
TITLE: Troubleshooting
UID: SDOC_TROUBLESHOOTING
VERSION: Git commit: @GIT_VERSION, Git branch: @GIT_BRANCH
DATE: @GIT_COMMIT_DATETIME
OPTIONS:
  ENABLE_MID: True
  VIEW_STYLE: Narrative

[GRAMMAR]
ELEMENTS:
- TAG: SECTION
  PROPERTIES:
    IS_COMPOSITE: True
  FIELDS:
  - TITLE: MID
    TYPE: String
    REQUIRED: False
  - TITLE: UID
    TYPE: String
    REQUIRED: False
  - TITLE: TITLE
    TYPE: String
    REQUIRED: True
- TAG: TEXT
  FIELDS:
  - TITLE: MID
    TYPE: String
    REQUIRED: False
  - TITLE: STATEMENT
    TYPE: String
    REQUIRED: True
  RELATIONS:
  - TYPE: Parent
  - TYPE: File

[TEXT]
MID: 7e3481d51ad14767b5c97132cad2e0a6
STATEMENT: >>>
This document summarizes solutions to the most common issues reported by
StrictDoc users.
<<<

[[SECTION]]
MID: 17152ac7de9f4c138b85e2956091206f
TITLE: Caching issues

[TEXT]
MID: 9a32ac13510d401cbc1a608259652c78
STATEMENT: >>>
.. note::

    **TL;DR:** If you encounter errors related to reading data, make sure to delete the StrictDoc cache folder located at ``output/_cache`` or in the custom directory if specified by the ``cache_dir`` option in the ``strictdoc_config.py`` configuration file. See [LINK: SECTION-UG-Path-to-cache-dir].

StrictDoc caches many artifacts on disk. Some artifacts are cached using
Python’s `pickle <https://docs.python.org/3/library/pickle.html>`_ module, while
others are written directly to disk.

The pickle module serializes Python objects to disk. The issue with this
approach is that when StrictDoc changes the schema of its objects (e.g., when
SDocNode or SDocDocument objects gain a new property or a property type
changes), an outdated object may be read from the cache after upgrading to a new
StrictDoc version. While a more systematic solution might be implemented in the
future, the current workaround is to manually delete the StrictDoc cache folder.
<<<

[[/SECTION]]
