[DOCUMENT]
TITLE: Document 1

[[SECTION]]
TITLE: Section title

[TEXT]
STATEMENT: >>>
Text statement.
<<<

[REQUIREMENT]
UID: REQ-3
STATEMENT: >>>
Text statement.
<<<
RELATIONS:
- TYPE: Parent
  VALUE: REQ-1

[[/SECTION]]
