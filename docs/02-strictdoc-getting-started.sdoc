[DOCUMENT]
NAME: Getting started

[SECTION]
LEVEL: 1
TITLE: Installing StrictDoc as a Pip package

[FREETEXT]
.. code-block:: text

    pip install strictdoc
[/FREETEXT]

[/SECTION]

[SECTION]
LEVEL: 1
TITLE: Installing StrictDoc from GitHub (development)

[FREETEXT]
.. code-block:: text

    git clone git@github.com:stanislaw/strictdoc.git && cd strictdoc
    poetry install
    poetry run strictdoc
[/FREETEXT]

[/SECTION]

[SECTION]
LEVEL: 1
TITLE: Hello world

[FREETEXT]
.. code-block:: text

    git clone git@github.com:stanislaw/strictdoc.git && cd strictdoc
    strictdoc export docs/
[/FREETEXT]

[/SECTION]
