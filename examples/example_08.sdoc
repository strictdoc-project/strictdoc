[DOCUMENT]
TITLE: Example 8: Traceability between requirements and source files

[REQUIREMENT]
UID: REQ-001
REFS:
- TYPE: File
  VALUE: examples/example_source_files/file.py
TITLE: Whole file reference
STATEMENT: This requirement references the whole file.

[REQUIREMENT]
UID: REQ-002
REFS:
- TYPE: File
  VALUE: examples/example_source_files/file.py
TITLE: Source range reference
STATEMENT: This requirement references a range in the file.

[REQUIREMENT]
UID: REQ-003
REFS:
- TYPE: File
  VALUE: examples/example_source_files/file2.py
TITLE: Source range reference
STATEMENT: This requirement references a range in the file.
