[DOCUMENT]
TITLE: Document title

[TEXT]
STATEMENT: >>>
Hello world!
<<<

[SECTION]
TITLE: Section title

[TEXT]
STATEMENT: >>>
This is a free text of this section.
<<<

[/SECTION]

[REQUIREMENT]
STATEMENT: >>>
Requirement statement.
<<<
