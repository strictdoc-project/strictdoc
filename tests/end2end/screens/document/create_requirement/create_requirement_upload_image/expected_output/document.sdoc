[DOCUMENT]
MID: bec898434a504f4f9cbe671aaea90a19
TITLE: Document 1
OPTIONS:
  ENABLE_MID: True

[REQUIREMENT]
MID: 00112233445566778899AABBCCDDEEFF
UID: REQ-1
TITLE: First title
STATEMENT: >>>
.. image:: ./_assets/00112233445566778899AABBCCDDEEFF/picture.svg
<<<
