[DOCUMENT]
TITLE: Modelica description strings

[REQUIREMENT]
UID: TC-1
TITLE: Test case 1
STATEMENT: The check model checks the requirements.

[REQUIREMENT]
UID: REQ-1
TITLE: Requirement 1
STATEMENT: The output rises.

[REQUIREMENT]
UID: REQ-2
TITLE: Requirement 2
STATEMENT: The output falls.

[REQUIREMENT]
UID: REQ-3
TITLE: Requirement 3
STATEMENT: The output falls fast.
