[DOCUMENT]
TITLE: Document 1

[FREETEXT]
Hello world!
[/FREETEXT]

[REQUIREMENT]
UID: REQ-001
TITLE: Requirement title #1
STATEMENT: >>>
Requirement statement #1.
<<<
RELATIONS:
- TYPE: Parent
  VALUE: REQ-002
- TYPE: Parent
  VALUE: REQ-003
- TYPE: Parent
  VALUE: REQ-004

[REQUIREMENT]
UID: REQ-002
TITLE: Requirement title #2
STATEMENT: >>>
Requirement statement #2.
<<<

[REQUIREMENT]
UID: REQ-003
TITLE: Requirement title #3
STATEMENT: >>>
Requirement statement #3.
<<<

[REQUIREMENT]
UID: REQ-004
TITLE: Requirement title #4
STATEMENT: >>>
Requirement statement #4.
<<<
