[DOCUMENT]
MID: 8e68536f7d4047ada15d3a3043580c4a
TITLE: Design Document
UID: SDOC_DD
VERSION: Git commit: @GIT_VERSION, Git branch: @GIT_BRANCH
DATE: @GIT_COMMIT_DATETIME
PREFIX: SDOC-SRS-
OPTIONS:
  ENABLE_MID: True
  VIEW_STYLE: Narrative
  NODE_IN_TOC: True

[GRAMMAR]
ELEMENTS:
- TAG: SECTION
  PROPERTIES:
    IS_COMPOSITE: True
  FIELDS:
  - TITLE: MID
    TYPE: String
    REQUIRED: True
  - TITLE: UID
    TYPE: String
    REQUIRED: False
  - TITLE: LEVEL
    TYPE: String
    REQUIRED: False
  - TITLE: PREFIX
    TYPE: String
    REQUIRED: False
  - TITLE: TITLE
    TYPE: String
    REQUIRED: True
- TAG: TEXT
  FIELDS:
  - TITLE: MID
    TYPE: String
    REQUIRED: False
  - TITLE: STATEMENT
    TYPE: String
    REQUIRED: True
  RELATIONS:
  - TYPE: Parent
  - TYPE: File
- TAG: DESIGN
  FIELDS:
  - TITLE: MID
    TYPE: String
    REQUIRED: True
  - TITLE: UID
    TYPE: String
    REQUIRED: False
  - TITLE: TITLE
    TYPE: String
    REQUIRED: False
  - TITLE: STATEMENT
    TYPE: String
    REQUIRED: False
  RELATIONS:
  - TYPE: Parent
  - TYPE: File

[TEXT]
MID: 2c006e9044074d239db4a45328633657
STATEMENT: >>>
This document describes the architecture and the implementation details of
StrictDoc. Compared to the User Guide that describes how to use StrictDoc, this
Design Document focuses on the "how it works" of StrictDoc.
<<<

[[SECTION]]
MID: a74f4e7328714765b5e051768ca8383d
TITLE: Overview

[TEXT]
MID: 23937f96ac8e437d81686071cc42d6bf
STATEMENT: >>>
StrictDoc consists of two applications:

1. StrictDoc command-line application (CLI).
2. StrictDoc web application.

Both applications share a significant subset of the backend and frontend logic.
The backend logic is written in Python, the frontend logic is written using
HTML/CSS, Jinja templates, and the Turbo.js frontend library.
<<<

[[/SECTION]]

[[SECTION]]
MID: f296843b2027457f851a159abafc97e3
TITLE: Building blocks

[TEXT]
MID: bae7db5591fe418a857af4fb02ad4fec
STATEMENT: >>>
StrictDoc is based on the following open-source libraries and tools:

.. list-table::
   :header-rows: 1
   :widths: 15 85

   * - **Library/tool**
     - **Description**

   * - TextX
     - Used for StrictDoc grammar definition and parsing of the sdoc files.

   * - Jinja
     - Rendering HTML templates.

   * - Sphinx and Docutils
     - - Support of Restructured Text (reST) format
       - Generation of RST documents into HTML
       - Generation of RST documents into PDF using LaTeX
       - Generating documentation websites using Sphinx.

   * - FastAPI
     - Server used for StrictDoc's Web-based user interface.

   * - Turbo
     - Javascript library used for StrictDoc's Web-based user interface.

   * - Selenium and SeleniumBase
     - Used for end-to-end testing of StrictDoc's Web-based user interface.
<<<

[[/SECTION]]

[[SECTION]]
MID: 5328a6f4c8544f5e92a91279b5b2c0df
UID: SECTION-DD-High-level-architecture
TITLE: High-level architecture

[TEXT]
MID: dcb6369b8d0949f0b06c9ee5b2188b12
STATEMENT: >>>
The following diagram captures the high-level architecture of StrictDoc.

.. image:: _assets/StrictDoc_Workspace-Architecture.drawio.png
   :alt: StrictDoc's architecture diagram
   :class: image
   :width: 100%
<<<

[[/SECTION]]

[[SECTION]]
MID: 9b81ed50014c412bb617e90552e58879
TITLE: StrictDoc command-line application

[TEXT]
MID: 0e0fca629004496084dbe5e217874c36
STATEMENT: >>>
StrictDoc command-line application is at the core of StrictDoc. The command-line
interface contains commands for exporting/importing SDoc content from/to other
formats and presenting documentation content to a user.

The command-line application can be seen as a Model-View-Controller application:

- A command entered by a user gets recognized by the CLI arguments parser.
- Depending on the type of command, a responsible Action (Controller layer)
  processes the command (export action, import action, etc.).
- The input of the command is transformed by the action using the backend (Model
  layer) (SDoc, ReqIF, Excel, etc.).
- The resulting output is written back to HTML or other formats (View layer).
<<<

[[/SECTION]]

[[SECTION]]
MID: dbcfa8a98e4f4928b0b35938d57dd644
TITLE: StrictDoc web application

[TEXT]
MID: f84c0efa27954e44a8b5c1dd3517f90f
STATEMENT: >>>
StrictDoc Web application is based on FastAPI / Uvicorn. The end-to-end usage
cycle of the web application is as follows:

- A browser requests documents from a FastAPI server.
- The FastAPI web server parses the SDoc files into memory and converts them
  into HTML using Jinja templates. The resulting HTML output is given back to
  the user.
- The Jinja templates are extended with JavaScript logic that allows a user to
  edit the documents and send the updated content back to the server.
- The server writes the updated content back to the SDoc files stored on a
  user's file system.
<<<

[[SECTION]]
MID: dd2bd75fdffe49a1a0299b804538329c
TITLE: The HTML Over the Wire (Hotwire) architecture

[TEXT]
MID: 5577da2187294eb986ec84d9fe26bbdf
STATEMENT: >>>
StrictDoc uses the `Hotwire architecture <https://hotwired.dev>`_.

The JavaScript framework used by StrictDoc is minimized to Turbo.js, which
helps to avoid the complexity of the larger JS frameworks such as React, Vue,
Angular, etc. In accordance with the Hotwire approach, most of StrictDoc's
business logic is done on a server, while Turbo provides a thin layer of JS
and AJAX to connect the almost static HTML with the server.

The Hotwire approach helps to reduce the differences between the static HTML
produced by the StrictDoc command-line application and the StrictDoc web
application. In both cases, the core content of StrictDoc is a statically
generated website with documents. The web application extends the static HTML
content with Turbo to turn it into a dynamic website.

Currently, the web server renders the HTML documents using the same generators
that are used by the static HTML export, so the static HTML documentation and
the web application interface look identical. The web interface adds the action
buttons and other additional UI elements for editing the content.

Until 2026-07-24, StrictDoc used Stimulus.js for declarative controller
wiring. It was dropped for a number of reasons, most notably direct control
over what JavaScript loads and runs on each page, and the fact that Stimulus
assumes ES modules, while StrictDoc also exports as a static file:// site
with no module loader available — forcing a UMD build plus a dedicated
startup script to restore window.Stimulus.application after Turbo
re-executes head scripts on some navigations

All interactive behavior is now implemented as small, dependency-free JS
files. Where a script needs to react to newly inserted markup, it registers
through a single shared StrictDoc.onInsert contract instead of running its
own MutationObserver.
<<<

[[/SECTION]]

[[/SECTION]]

[[SECTION]]
MID: 50f1db3236fa426ea5904974ee724939
TITLE: Static HTML search

[DESIGN]
MID: 5fedd9aac1684adc8fe1f3b87557345d
UID: SDOC-SRS-156
TITLE: Static HTML search
STATEMENT: >>>
The static HTML search is implemented using a custom JavaScript solution that
consumes a search index JS file generated by the same StrictDoc Python pipeline
that produces all other artifacts.

The following requirements are relevant in the StrictDoc context:

- The JS library must start up quickly, so search indexes need to be generated
  in advance. Since StrictDoc is based on Python, index generation must be done
  in Python rather than in JS/NPM.
- The Python code must generate indexes incrementally and allow caching, e.g.,
  one index per document.
- The JS library must support matching search terms using OR by default and AND
  when the terms are enclosed in quotes, e.g., "foo bar".
- The JS library must support incremental and decremental search terms.

Several existing solutions, such as Lunr and FlexSearch, were considered, but
none were found to support all of the above features.

.. note::

    **Incremental/decremental** search means that a search index maintains the following additional terms for a word "foo" found in a document node with MID "abc":

    - "foo" => "abc"
    - "f" => "abc"
    - "fo" => "abc"
    - "o" => "abc"
    - "oo" => "abc"

The current implementation builds per-document indexes immediately after parsing
the SDoc documents from .sdoc files. The generated index is cached along with
the overall document content, significantly speeding up tree generation once the
document caches are available. StrictDoc generates a JSON file containing a
search index ``{ search term => node MID }`` as well as a map ``{ MID => SDoc
node }``.

The corresponding JS file has access to the pre-built search indexes generated
by Python. The JavaScript algorithms are simple but enable basic search
functionality:

- Incremental/decremental search for terms using OR when multiple terms are
  provided without quotes, and AND when the terms are quoted. Currently, only
  one quoted search term is supported.
- The algorithm is reasonably fast and has been tested with documentation trees
  of up to 130+ documents with the largest documents reaching up to 1.5
  megabytes.
<<<
RELATIONS:
- TYPE: Parent
  VALUE: SDOC-SRS-155

[[/SECTION]]

[[SECTION]]
MID: 108af17c077c48bea04557c9d325e924
TITLE: Parsing SDoc files

[TEXT]
MID: 8a926f0a67424a1eb5db73bb5abca0cd
STATEMENT: >>>
StrictDoc uses `textX <https://github.com/textX/textX>`_  which is a
``meta-language for building Domain-Specific Languages (DSLs) in Python``. The
textX itself is based on `Arpeggio <https://github.com/textX/Arpeggio>`_ which
is a ``Parser interpreter based on PEG grammars written in Python``.

StrictDoc relies on both tools to get:

- A declarative grammar description
- Automatic conversion of the parsed blocks into Python objects
- Fast parsing of SDoc files.

One important implementation detail of Arpeggio that influences StrictDoc user
experience is that the parser stops immediately when it encounters an error. For
a document that has several issues, the parser highlights only the first error
without going any further. When the first error is resolved, the second error
will be shown, etc.
<<<

[[/SECTION]]

[[SECTION]]
MID: 4db723c7ae2c4350b2f184783cb638e7
UID: SECTION-DD-Caching-artifacts
TITLE: Caching artifacts

[TEXT]
MID: d351d1bf6c2a48d88e9b9bdc50e029ff
STATEMENT: >>>
StrictDoc caches artifacts to disk to speed up performance by avoiding repeated
reading and computation of already-parsed objects.

The cached artifacts include:

- Precompiled Jinja templates
- RST fragments converted to HTML
- Pickled Python objects from parsed SDoc files
- Pickled Python objects from parsed source files
- Git revisions used for the Diff/Changelog feature.

A general algorithm is as follows:

An MD5 checksum is generated for a piece of content, and a file with this
checksum in its name is written to disk. On subsequent reads, the checksum is
recalculated, and the disk is checked for an existing file with the matching
checksum. If a match is found, the file is read from disk, avoiding the need for
extensive parsing or computation.
<<<

[[/SECTION]]

[[SECTION]]
MID: 4b904b71438c47fcac8aba14df2dd7c0
TITLE: HTML escaping

[TEXT]
MID: e8a03713c7f644698d9a72cc79b2a299
STATEMENT: >>>
StrictDoc uses Jinja2 autoescaping_ for HTML output. `Template.render`_ calls
will escape any Python object unless it's explicitly marked as safe.

Good to know for a start:

- If a Python object intentionally contains HTML it must be marked as safe
  to bypass autoescaping. Templates can do this by piping to safe_, or Python code
  can do it by wrapping an object into `markupsafe.Markup`_.
- Passing text to the `Markup() <markupsafe.Markup_>`_ constructor marks that text
  as safe, but *does not escape* it.
- Text can be explicitly escaped with `markupsafe.escape`_. It's similar to
  `html.escape`_, but the result is immediately marked safe.
- `markupsafe.Markup`_ is responsible for some "magic". It's a :code:`str` subclass
  with the same methods, but escaping arguments. For example,
  :code:`"> " + Markup("<div>safe</div>")` will turn into :code:`"&gt; <div>safe</div>"`,
  thanks to :code:`__radd__` in this specific case. To prevent escaping,
  you would use :code:`Markup("> ") + Markup("<div>safe</div>")`. Basically the
  same magic happens in templates when using safe_.
- See also `Working with Automatic Escaping`_.

.. _autoescaping: https://jinja.palletsprojects.com/en/latest/api/#autoescaping
.. _Working with Automatic Escaping: https://jinja.palletsprojects.com/en/latest/templates/#working-with-automatic-escaping
.. _markupsafe.Markup: https://markupsafe.palletsprojects.com/en/latest/escaping/#markupsafe.Markup
.. _markupsafe.escape: https://markupsafe.palletsprojects.com/en/latest/escaping/#markupsafe.escape
.. _safe: https://jinja.palletsprojects.com/en/latest/templates/#jinja-filters.safe
.. _Template.render: https://jinja.palletsprojects.com/en/latest/api/#jinja2.Template.render
.. _html.escape: https://docs.python.org/3/library/html.html#html.escape
<<<

[[/SECTION]]

[[SECTION]]
MID: 92e8709709614f0f9ccdf702799bf56c
TITLE: ReqIF interface

[DESIGN]
MID: abe8709709614f0f9ccdf702799bf511
UID: SDOC-SRS-153
TITLE: ReqIF-to-SDoc import
STATEMENT: >>>
The following details describe the implementation of the StrictDoc ReqIF-to-SDoc
converter.

The table below shows how ReqIF elements are mapped to SDoc elements:

.. list-table:: **Table: Mapping between ReqIF elements and SDoc elements**
    :widths: 50 50
    :header-rows: 1

    * - ReqIF Element
      - SDoc Element

    * - Specification
      - Document

    * - Spec Object Type
      - Grammar Element

    * - Spec Object
      - Node

Before converting ReqIF elements to SDoc elements, StrictDoc first traverses the
entire XML file. This is necessary because a single ReqIF file may contain
multiple specifications, and it is otherwise not possible to determine which
Spec Object Types, Spec Relations, or Spec Relation Types are used by which
specification or whether they are used at all.

StrictDoc uses a **lazy** approach to generating SDoc documents from a ReqIF XML
file. For each ReqIF Specification, only the elements that are actually used by
that specification will be included in the corresponding SDoc document.

**Example:**

If ReqIF Specification “A” uses Spec Object Type “X”, and Specification “B” uses
Spec Relation Type “Y”, the resulting SDoc documents will be:

* SDoc document “A” with a grammar element for type “X”
* SDoc document “B” with a grammar element for type “Y”
<<<

[[/SECTION]]
