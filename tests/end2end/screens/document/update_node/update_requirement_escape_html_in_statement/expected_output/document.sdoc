[DOCUMENT]
TITLE: Document 1

[REQUIREMENT]
TITLE: Requirement title
STATEMENT: >>>
`Link does not get corrupted <https://github.com/strictdoc-project/sphinx-latex-reqspec-template>`_

`Link does not get corrupted <https://github.com/strictdoc-project/sphinx-latex-reqspec-template>`_

`Link does not get corrupted <https://github.com/strictdoc-project/sphinx-latex-reqspec-template>`_
<<<
