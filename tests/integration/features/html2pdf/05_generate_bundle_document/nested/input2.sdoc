[DOCUMENT]
TITLE: Dummy Software Requirements Specification #2
UID: DOC-2
VERSION: 2.0
DATE: 2026-02-02
CLASSIFICATION: Internal
METADATA:
  AUTHOR: Jane Doe

[TEXT]
STATEMENT: >>>
.. image:: _assets/file.svg
   :alt: Test image
   :class: image
   :width: 100%
<<<
