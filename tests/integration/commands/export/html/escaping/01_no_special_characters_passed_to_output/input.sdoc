[DOCUMENT]
TITLE: <b>"escaping" & 'document title'</b>

[SECTION]
TITLE: <b>"escaping" & 'section title'</b>

[TEXT]
STATEMENT: >>>
<b>"escaping" & 'text statement'</b>
<<<

[REQUIREMENT]
STATEMENT: >>>
<b>"escaping" & 'requirement statement'</b>
<<<

[/SECTION]
