[DOCUMENT]
TITLE: TEST DOCUMENT

[REQUIREMENT]
UID: REQ-01
TITLE: Test_REQ
STATEMENT: >>>
This requirement shall link to source files.
<<<
RELATIONS:
- TYPE: File
  VALUE: src/file1.py
- TYPE: File
  VALUE: src/file2.py
