[DOCUMENT]
TITLE: Document 1

[REQUIREMENT]
UID: REQ-001
TITLE: Requirement title
STATEMENT: >>>
Requirement statement.
<<<
RATIONALE: >>>
Requirement rationale.
<<<
RELATIONS:
- TYPE: Parent
  VALUE: REQ-002

[REQUIREMENT]
UID: REQ-002
TITLE: Parent requirement
