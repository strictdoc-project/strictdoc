[DOCUMENT]
TITLE: Test Document
OPTIONS:
  REQUIREMENT_STYLE: Inline
  DEFAULT_VIEW: EXISTING_VIEW
VIEWS:
- ID: EXISTING_VIEW
  NAME: Existing view
  TAGS:
  - OBJECT_TYPE: REQUIREMENT
    VISIBLE_FIELDS:
    - NAME: UID
      PLACEMENT: XYZ
    - NAME: STATEMENT
