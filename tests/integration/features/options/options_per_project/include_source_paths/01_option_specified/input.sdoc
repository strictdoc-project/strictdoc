[DOCUMENT]
TITLE: Hello world doc

[TEXT]
STATEMENT: >>>
**Hello world**
<<<

[REQUIREMENT]
UID: REQ-001
RELATIONS:
- TYPE: File
  VALUE: src1/test1.py

[REQUIREMENT]
UID: REQ-002
RELATIONS:
- TYPE: File
  VALUE: src2/test2.py
