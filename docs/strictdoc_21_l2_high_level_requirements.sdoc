[DOCUMENT]
MID: 8a87daf19a7c487f89f396406a974509
TITLE: StrictDoc High-Level Requirements (L2)
VERSION: Git commit: @GIT_VERSION, Git branch: @GIT_BRANCH
DATE: @GIT_COMMIT_DATETIME
PREFIX: SDOC-SRS-
OPTIONS:
  ENABLE_MID: True

[GRAMMAR]
ELEMENTS:
- TAG: SECTION
  PROPERTIES:
    IS_COMPOSITE: True
    VIEW_STYLE: Narrative
  FIELDS:
  - TITLE: MID
    TYPE: String
    REQUIRED: False
  - TITLE: UID
    TYPE: String
    REQUIRED: False
  - TITLE: TITLE
    TYPE: String
    REQUIRED: True
- TAG: TEXT
  FIELDS:
  - TITLE: MID
    TYPE: String
    REQUIRED: True
  - TITLE: UID
    TYPE: String
    REQUIRED: False
  - TITLE: STATEMENT
    TYPE: String
    REQUIRED: False
- TAG: REQUIREMENT
  PROPERTIES:
    VIEW_STYLE: Table
  FIELDS:
  - TITLE: MID
    TYPE: String
    REQUIRED: False
  - TITLE: UID
    TYPE: String
    REQUIRED: False
  - TITLE: STATUS
    TYPE: String
    REQUIRED: False
  - TITLE: TITLE
    TYPE: String
    REQUIRED: False
  - TITLE: STATEMENT
    TYPE: String
    REQUIRED: False
  - TITLE: RATIONALE
    TYPE: String
    REQUIRED: False
  - TITLE: COMMENT
    TYPE: String
    REQUIRED: False
  RELATIONS:
  - TYPE: Parent
  - TYPE: File

[[SECTION]]
MID: bd8a7931c1e04df9bf08d291488c67aa
TITLE: SDoc data model

[REQUIREMENT]
MID: e8d5b55055254144b96d1ffeb587ec72
UID: SDOC-SRS-18
STATUS: Active
TITLE: Data model
STATEMENT: >>>
StrictDoc shall be based on a data model.
<<<
RATIONALE: >>>
Designing StrictDoc with a goal of having a consistent data model ensures that
the tool:

1) can support a rich set of use cases,
2) model the existing documentation templates used by the industries,
3) interface well with other formats for storing documentation and requirements,
   e.g., ReqIF and SPDX.
<<<
COMMENT: >>>
Verification: data model diagram TBD.
<<<
RELATIONS:
- TYPE: Parent
  VALUE: SDOC-SSS-88
- TYPE: Parent
  VALUE: SDOC-SSS-58

[REQUIREMENT]
MID: 3b31cad22529476db01aca41caf39750
UID: SDOC-SRS-26
STATUS: Active
TITLE: Requirement model
STATEMENT: >>>
StrictDoc's data model shall support modeling requirements.
<<<
RELATIONS:
- TYPE: Parent
  VALUE: SDOC-SSS-4

[REQUIREMENT]
MID: 8e2ffffd33af4a969d5bb7ca40cb49a4
UID: SDOC-SRS-100
STATUS: Active
TITLE: Requirement model fields
STATEMENT: >>>
StrictDoc's "Requirement" model shall support configurable fields system.
<<<
RELATIONS:
- TYPE: Parent
  VALUE: SDOC-SSS-62

[REQUIREMENT]
MID: 2d4020ba06d74571aef7aafe8604215b
UID: SDOC-SRS-132
STATUS: Active
TITLE: Requirement model default fields
STATEMENT: >>>
By default, the Requirement shall support the following fields:

- MID
- UID
- STATUS
- TITLE
- STATEMENT
- RATIONALE
- COMMENT.
<<<
RATIONALE: >>>
These fields are the most typical fields found in requirement documents.
<<<
RELATIONS:
- TYPE: Parent
  VALUE: SDOC-SSS-61

[REQUIREMENT]
MID: f94419a390f2403daa3c4cd0e96f6cb6
UID: SDOC-SRS-98
STATUS: Active
TITLE: Document model
STATEMENT: >>>
StrictDoc's data model shall support modeling documents.
<<<
RELATIONS:
- TYPE: Parent
  VALUE: SDOC-SSS-64

[REQUIREMENT]
MID: 435f856197d743c1b9b1dcbe91a22863
UID: SDOC-SRS-110
STATUS: Active
TITLE: Document metadata
STATEMENT: >>>
StrictDoc's data model shall support a Document metadata model including at
least:

- UID
- Document version
- Document classification
- Document authors.
<<<
RELATIONS:
- TYPE: Parent
  VALUE: SDOC-SSS-53
- TYPE: Parent
  VALUE: SDOC-SSS-75

[REQUIREMENT]
MID: abcced8724d743c1b9b1dcbe91a22863
UID: SDOC-SRS-151
STATUS: Active
TITLE: Document configuration
STATEMENT: >>>
StrictDoc's data model shall support configuring the document options:

- Enable/disable MID
- Markup choice, e.g., RST, HTML, etc.
- Levels (automatic or manual)
- Node style
- Default presentation view.
<<<
RELATIONS:
- TYPE: Parent
  VALUE: SDOC-SSS-53
- TYPE: Parent
  VALUE: SDOC-SSS-75

[REQUIREMENT]
MID: 63821c507d584cf985f05904710b9779
UID: SDOC-SRS-99
STATUS: Active
TITLE: Section model
STATEMENT: >>>
StrictDoc's data model shall support a concept of a "Section" which nests other
Sections, Requirements, Texts.
<<<
RATIONALE: >>>
"Section" corresponds to a chapter or a section in a document and helps to
organize a document by grouping text nodes, requirements and other sections.
<<<
RELATIONS:
- TYPE: Parent
  VALUE: SDOC-SSS-51

[REQUIREMENT]
MID: 899d2f68749b4be1a3124fe4d01de1aa
UID: SDOC-SRS-135
STATUS: Active
TITLE: Free text
STATEMENT: >>>
StrictDoc's data model shall support a "Free Text" model, representing
non-normative documentation content.
<<<
RATIONALE: >>>
Documentation comprises normative components, such as uniquely identifiable
elements like requirements or design items, and non-normative components,
including introductory text, overview chapters, and other content. The
non-normative parts help provide a general understanding for the reader but do
not contribute to traceability information. StrictDoc's free text is designed to
store this type of non-normative information in SDoc documents.
<<<
RELATIONS:
- TYPE: Parent
  VALUE: SDOC-SSS-3

[REQUIREMENT]
MID: 983653fc26214f46977dc792d65ae65f
UID: SDOC-SRS-109
STATUS: Active
TITLE: Composeable document
STATEMENT: >>>
StrictDoc's data model shall allow composing a Document from other Documents.
<<<
RATIONALE: >>>
The logic behind the parent requirement remains fully relevant. Additionally, an
alternative approach could involve using a dedicated entity, like "Fragment", to
allow a Document to be composed of includable sections or document fragments.
Managing composition at the Document level eliminates the need in additional
entities like "Fragment", streamlining both the conceptual understanding and the
practical implementation of composability.
<<<
COMMENT: >>>
The corresponding UI capability for Fragments CRUD is TBD.
<<<
RELATIONS:
- TYPE: Parent
  VALUE: SDOC-SSS-52
- TYPE: Parent
  VALUE: DO178-4

[REQUIREMENT]
MID: fad4cf5dcf4d40518c7c9826fd6bd18a
UID: SDOC-SRS-31
STATUS: Active
TITLE: Requirement relations
STATEMENT: >>>
The StrictDoc data model shall support connecting requirements using Parent and
Child relations.
<<<
RATIONALE: >>>
Support of both Parent and Child relations allows to build typical requirements
relations such as child-to-parent and less common relations when one document
can have parent links to a parent document and child links to a child document
(e.g., the so-called "compliance" or "tailoring matrix" documents may use this
structure).
<<<
RELATIONS:
- TYPE: Parent
  VALUE: SDOC-SSS-7
- TYPE: Parent
  VALUE: SDOC-SSS-48

[REQUIREMENT]
MID: 9930894b08c44f5eba996c0a255e9e3f
UID: SDOC-SRS-101
STATUS: Active
TITLE: Requirement relation roles
STATEMENT: >>>
Each SDoc relation shall be optionally configurable with a relation role.

NOTE: A relation role is a string value. Typical examples: "refines",
"verifies", "implements".
<<<
RELATIONS:
- TYPE: Parent
  VALUE: SDOC-SSS-8

[REQUIREMENT]
MID: fa090bc6976c4275aadbf522da6b920b
UID: SDOC-SRS-149
STATUS: Active
TITLE: Inline links
STATEMENT: >>>
StrictDoc shall support referencing any node by embedding a hyperlink within the
text content of another node.
<<<
RATIONALE: >>>
The inline links do not replace the relations between SDoc nodes. Instead, an
inline link could be an easy way to refer from one textual node to a chapter or
a document. A common use case is "See section ABC for more details".
<<<

[REQUIREMENT]
MID: 54132bc6976c4275aadbf522da6b920b
UID: SDOC-SRS-150
STATUS: Active
TITLE: Inline anchors
STATEMENT: >>>
StrictDoc shall support adding anchors within the text content of any node, such
that these anchors can be referenced by inline links from other nodes.
<<<
RATIONALE: >>>
Anchors allow authors to define precise reference points within SDoc node
fields.
<<<

[[SECTION]]
MID: 26a0233258ec4d7ab6338d915ddea3e6
TITLE: Capability: Automatic generation of UID

[REQUIREMENT]
MID: 1ff58c59c8ab48cdabfba942ba98bab7
UID: SDOC-SRS-206
STATUS: Active
TITLE: Default UID generation algorithm
STATEMENT: >>>
StrictDoc shall generate a missing UID for a node according to the following
algorithm:

- The node's applicable UID prefix shall be resolved by evaluating, in order
  of precedence: the node's own PREFIX field, the grammar element's PREFIX
  property, the parent section's prefix, and the document's PREFIX setting,
  which shall default to "REQ-" if not configured.
- The highest numeric suffix currently in use with the resolved prefix shall
  be determined by scanning the entire document tree.
- The node shall be assigned a UID composed of the resolved prefix and the
  next unused integer suffix, computed as the highest existing suffix
  incremented by one, or one if no existing suffix is found.
- Where multiple nodes share the same resolved prefix and lack a UID,
  consecutive integer suffixes shall be assigned to them in document order.
<<<

[REQUIREMENT]
MID: 4ed550f6074c4d8cb27196184f7fe234
UID: SDOC-SRS-207
STATUS: Active
TITLE: Custom UID algorithms
STATEMENT: >>>
StrictDoc shall allow a user to customize the UID algorithm to their needs.
<<<
COMMENT: >>>
An example of a custom algorithm suggested by a user:

The expected behavior could be:

- The prefix of a type is defined in the grammar.
- A document can optionally define an additional prefix.
- If both prefixes are present, they are concatenated.
- If only the grammar prefix is present, it is used on its own.
- If only the document prefix is present, it is used on its own.
- If neither is present, the existing behavior should be preserved.
<<<

[[/SECTION]]

[[/SECTION]]

[[SECTION]]
MID: cbc7f72c6e0b4c858817bf17357105a5
TITLE: SDoc text markup

[REQUIREMENT]
MID: 27a6da48c65445539e536ee034921fb5
UID: SDOC-SRS-20
STATUS: Active
TITLE: SDoc markup language
STATEMENT: >>>
StrictDoc shall implement its own text markup language called S-Doc
(strict-doc).
<<<
RATIONALE: >>>
The most commonly used Markdown format lacks the ability to store requirements
metadata. While the RST syntax does allow for customization with directives to
implement metadata extensions, its visual appearance contradicts other
requirements of StrictDoc, such as the type-safety of the grammar and visual
readability. Therefore, a markup language tailored specifically to the needs of
the requirements tool provides direct control over the capabilities implemented
in both the markup and the user interface.
<<<
RELATIONS:
- TYPE: Parent
  VALUE: SDOC-SSS-88
- TYPE: File
  VALUE: strictdoc/backend/sdoc/grammar/grammar.py
- TYPE: File
  VALUE: strictdoc/backend/sdoc/grammar/grammar_builder.py
- TYPE: File
  VALUE: strictdoc/backend/sdoc/reader.py
- TYPE: File
  VALUE: strictdoc/backend/sdoc/writer.py
- TYPE: File
  VALUE: strictdoc/backend/sdoc/processor.py

[REQUIREMENT]
MID: 1f147feed60245378de2e099facd196d
UID: SDOC-SRS-136
STATUS: Active
TITLE: Identical SDoc content by import/export roundtrip
STATEMENT: >>>
StrictDoc shall ensure that identical SDoc content is produced every time
StrictDoc reads an SDoc file and then writes it to another SDoc file.
<<<
RATIONALE: >>>
A consistent import/export roundtrip implementation and testing reduces the risk
of the SDoc bi-directional import/export corruption.
<<<
RELATIONS:
- TYPE: File
  FORMAT: Sourcecode
  VALUE: tests/unit/strictdoc/backend/sdoc/test_dsl_passthrough.py
- TYPE: File
  FORMAT: Sourcecode
  VALUE: tests/unit/strictdoc/backend/sdoc/test_dsl_passthrough_document_views.py
- TYPE: File
  FORMAT: Sourcecode
  VALUE: tests/unit/strictdoc/backend/sdoc/test_dsl_passthrough_grammar.py
- TYPE: File
  FORMAT: Sourcecode
  VALUE: tests/unit/strictdoc/backend/sdoc/test_dsl_passthrough_relations.py
- TYPE: Parent
  VALUE: SDOC-SSS-94

[REQUIREMENT]
MID: f48a57c0cd764951a667127ce92fdb12
UID: SDOC-SRS-127
STATUS: Active
TITLE: SDoc and Git storage
STATEMENT: >>>
StrictDoc shall assume and implement capabilities for storage of SDoc files
using Git version control system.
<<<
RELATIONS:
- TYPE: Parent
  VALUE: SDOC-SSS-87
- TYPE: Parent
  VALUE: SDOC-SSS-33
- TYPE: Parent
  VALUE: SDOC-SSS-84
- TYPE: Parent
  VALUE: SDOC-SSS-94

[REQUIREMENT]
MID: 9df34a7ab79842d99ee68303f334d4eb
UID: SDOC-SRS-104
STATUS: Active
TITLE: SDoc file extension
STATEMENT: >>>
The SDoc markup content shall be stored in files with .sdoc extension.
<<<
RATIONALE: >>>
Given that the name of the model is S-Doc (strict-doc), it is reasonable to make
the document files have the ``.sdoc`` extension. This helps to identify the
document files.
<<<
RELATIONS:
- TYPE: Parent
  VALUE: SDOC-SSS-80

[REQUIREMENT]
MID: 8dd6dd3979484dadbe71ac91aab50608
UID: SDOC-SRS-105
STATUS: Active
TITLE: One document per one SDoc file
STATEMENT: >>>
StrictDoc's SDoc file shall represent content of a single document.
<<<
COMMENT: >>>
A "Document" corresponds to a "Document" of the SDoc data model.
<<<
RELATIONS:
- TYPE: Parent
  VALUE: SDOC-SSS-64
- TYPE: Parent
  VALUE: DO178-1

[REQUIREMENT]
MID: e5e3033c13f24fa083423230da7994f7
UID: SDOC-SRS-19
STATUS: Active
TITLE: Fixed grammar
STATEMENT: >>>
StrictDoc's markup language shall be based on a well-defined grammar.
<<<
RELATIONS:
- TYPE: Parent
  VALUE: DO178-2
- TYPE: Parent
  VALUE: SDOC-SSS-55
- TYPE: Parent
  VALUE: SDOC-SSS-54
- TYPE: Parent
  VALUE: SDOC-SSS-94

[REQUIREMENT]
MID: b97418ceccff438cb0457ed4bdf1be47
UID: SDOC-SRS-93
STATUS: Active
TITLE: Default grammar fields
STATEMENT: >>>
The StrictDoc grammar shall have at least the following fields activated by
default:

- UID
- STATUS
- TITLE
- STATEMENT
- RATIONALE
- COMMENT
- RELATIONS (references to other requirements)
<<<
RELATIONS:
- TYPE: Parent
  VALUE: SDOC-SSS-61

[REQUIREMENT]
MID: 8924c29136944f65ac5efc8b6b90a07b
UID: SDOC-SRS-21
STATUS: Active
TITLE: Custom grammar / fields
STATEMENT: >>>
The SDoc markup shall support custom grammars.
<<<
RATIONALE: >>>
A custom grammar allows a user to define their own configuration of requirement
fields.
<<<
RELATIONS:
- TYPE: Parent
  VALUE: SDOC-SSS-62

[REQUIREMENT]
MID: 10d23bfbf4504c2e8c995ae89c500be4
UID: SDOC-SRS-122
STATUS: Active
TITLE: Importable grammars
STATEMENT: >>>
StrictDoc shall support an inclusion of a grammar stored in a separate file.
<<<
RATIONALE: >>>
A single grammar defined for several documents helps to standardize the
structure of all documents in a documentation tree and removes the effort needed
to create identical grammars all the time.
<<<
RELATIONS:
- TYPE: Parent
  VALUE: DO178-9
- TYPE: Parent
  VALUE: SDOC-SSS-52
- TYPE: File
  VALUE: strictdoc/backend/sdoc/grammar_reader.py
- TYPE: File
  VALUE: strictdoc/backend/sdoc/grammar/grammar_grammar.py

[REQUIREMENT]
MID: 5405c74a9eba4e9193007f01ea98bc85
UID: SDOC-SRS-22
STATUS: Active
TITLE: UID identifier format
STATEMENT: >>>
The SDoc markup shall only accept UID identifiers that consist of alphanumeric
characters separated by a limited set of ("_", "-", ".") characters (TBD).
<<<
RATIONALE: >>>
A standardized UID format supports easier unique identification of requirements.
It is easier to visually identify UIDs that look similar and common to a given
industry.
<<<
COMMENT: >>>
This requirement may need a revision to accommodate for more UID formats.
<<<
RELATIONS:
- TYPE: Parent
  VALUE: SDOC-SSS-89

[REQUIREMENT]
MID: f871dfc381354daf820cc1e2b94fdb05
UID: SDOC-SRS-24
STATUS: Active
TITLE: Format-specific markup-to-HTML fragment writers
STATEMENT: >>>
StrictDoc shall render supported markup formats (at least RST and Markdown) to
HTML fragments via dedicated format-specific writers selected by markup type.
<<<
RELATIONS:
- TYPE: Parent
  VALUE: SDOC-SSS-63

[REQUIREMENT]
MID: b1b4f03d4e404a14be481626803fcfc2
UID: SDOC-SRS-27
STATUS: Active
TITLE: MathJAX
STATEMENT: >>>
StrictDoc's markup language shall support integration with MathJax.
<<<
RELATIONS:
- TYPE: Parent
  VALUE: SDOC-SSS-63

[REQUIREMENT]
MID: 39f117b79cfa4a8485c458280b3d36ce
UID: SDOC-SRS-23
STATUS: Active
TITLE: No indentation
STATEMENT: >>>
SDoc text markup blocks shall all start from column 1, i.e., the nesting of the
blocks is not allowed.
<<<
RATIONALE: >>>
Nesting large text blocks of free text and requirements compromises readability.
<<<
RELATIONS:
- TYPE: Parent
  VALUE: SDOC-SSS-55

[REQUIREMENT]
MID: 98628e1db3ca4f52b7632674b69dd657
UID: SDOC-SRS-25
STATUS: Active
TITLE: Type-safe fields
STATEMENT: >>>
SDoc markup shall provide "type safety" for all fields.

NOTE: "Type safety" means that each field has a type and a corresponding set of
validation checks.
<<<
RELATIONS:
- TYPE: Parent
  VALUE: SDOC-SSS-55
- TYPE: File
  FORMAT: Sourcecode
  VALUE: strictdoc/backend/sdoc/grammar/type_system.py
- TYPE: Parent
  VALUE: SDOC-SSS-94

[[/SECTION]]

[[SECTION]]
MID: 8e175c1aff9c4bc1b20b032d6811e853
TITLE: Markdown markup

[REQUIREMENT]
MID: 1e1685d8be084a6c98729daae5637860
UID: SDOC-SRS-202
STATUS: Active
TITLE: Markdown support
STATEMENT: >>>
StrictDoc shall support Markdown markup.
<<<
RATIONALE: >>>
Markdown is the most popular markup language among programmers. Compared to the
StrictDoc native SDoc markup, Markdown is much more familiar to developers,
which lowers the entry barrier for writing formal requirements with StrictDoc or
other tools. It is also used extensively by AI tools.
<<<

[[/SECTION]]

[[SECTION]]
MID: 34b4abc6bb4649de9e56af31c229b0d1
UID: SECTION-SRS-Graph-database
TITLE: Graph database

[REQUIREMENT]
MID: 2c8d7940a23c443f81a7eb373340894e
UID: SDOC-SRS-28
STATUS: Active
TITLE: Traceability index
STATEMENT: >>>
StrictDoc shall maintain a complete Traceability Index of all documentation- and
requirements-related information available in a project tree.
<<<
RELATIONS:
- TYPE: Parent
  VALUE: SDOC-SSS-7

[REQUIREMENT]
MID: 272b8933276d4cd48a78fcfa11899573
UID: SDOC-SRS-29
STATUS: Active
TITLE: Uniqueness UID in tree
STATEMENT: >>>
For each requirement node, the Traceability Index shall ensure its uniqueness
throughout the node's lifecycle.
<<<
RATIONALE: >>>
The requirement ensures that the Traceability Index takes of care of validating
the uniqueness of all nodes in a document/requirements graph.
<<<
RELATIONS:
- TYPE: Parent
  VALUE: SDOC-SSS-89
- TYPE: Parent
  VALUE: SDOC-SSS-94

[REQUIREMENT]
MID: 8330d61fd5b1438fa90f127f88903a0d
UID: SDOC-SRS-30
STATUS: Active
TITLE: Detect links cycles
STATEMENT: >>>
The Traceability Index shall detect cycles between requirements.
<<<
RELATIONS:
- TYPE: Parent
  VALUE: SDOC-SSS-47
- TYPE: File
  FORMAT: Sourcecode
  VALUE: strictdoc/core/tree_cycle_detector.py
- TYPE: Parent
  VALUE: SDOC-SSS-94

[REQUIREMENT]
MID: 07a1e7bef11d4fcca86cd31ee5245d8d
UID: SDOC-SRS-32
STATUS: Active
TITLE: Link document nodes
STATEMENT: >>>
The Traceability Index shall recognize and maintain the relations between all
documents of a project tree.
<<<
RATIONALE: >>>
The relations between all documents are a summary of all relations between these
documents' requirements. This information is useful for:

1) Structural analysis of a requirements/documents graph.
2) Incremental regeneration of only those documents whose content was modified.
<<<
RELATIONS:
- TYPE: Parent
  VALUE: SDOC-SSS-47
- TYPE: Parent
  VALUE: SDOC-SSS-13
- TYPE: Parent
  VALUE: SDOC-SSS-14

[REQUIREMENT]
MID: 2dad5f293bc442eaa98859c4b5eac0d5
UID: SDOC-SRS-102
STATUS: Active
TITLE: Automatic resolution of reverse relations
STATEMENT: >>>
The StrictDoc's graph database shall maintain the requirement relations and
their reverse relations as follows:

- For a Parent relation, the database shall calculate the reverse Child
  relation.
- For a Child relation, the database shall calculate the reverse Parent
  relation.
<<<
RATIONALE: >>>
The calculation of the reverse relations allows the user interface code to get
and display both requirement's parent and child relations.
<<<
COMMENT: >>>
Example: If a child requirement REQ-002 has a parent requirement REQ-001, the
graph database first reads the link ``REQ-002 -Parent> REQ-001``, then it
creates a corresponding ``REQ-001 -Child> REQ-002`` on the go. Both relations
can be queried as follows, in pseudocode:

.. code-block::

    get_parent_requirements(REQ-002) == [REQ-001]
    get_children_requirements(REQ-001) == [REQ-002]
<<<
RELATIONS:
- TYPE: Parent
  VALUE: SDOC-SSS-71
- TYPE: Parent
  VALUE: SDOC-SSS-48

[[/SECTION]]

[[SECTION]]
MID: 4dce611287954289b1c2a6a15c413611
TITLE: Documentation tree

[REQUIREMENT]
MID: 50b2d5d6eb1140f0a2b980203468a5f7
UID: SDOC-SRS-115
STATUS: Active
TITLE: Finding documents recursively
STATEMENT: >>>
StrictDoc shall discover SDoc documents recursively based on a specified input
path.
<<<
RATIONALE: >>>
Recursive search allows working with documents located in multiple folders,
potentially spanning over several Git repositories.
<<<
RELATIONS:
- TYPE: Parent
  VALUE: SDOC-SSS-34
- TYPE: Parent
  VALUE: DO178-3

[[/SECTION]]

[[SECTION]]
MID: fcbf717009ce4cb2a8def7eb7b377654
UID: SECTION-SRS-Web-HTML-frontend
TITLE: Web/HTML frontend

[[SECTION]]
MID: a3603184d571449792f5cd752c978686
UID: SECTION-SRS-General-export-requirements-2
TITLE: General export requirements

[REQUIREMENT]
MID: 37f17fdd57ff47e9b7f4147adaeabde1
UID: SDOC-SRS-49
STATUS: Active
TITLE: Export to static HTML website
STATEMENT: >>>
StrictDoc shall support generating requirements documentation into static HTML.
<<<
RELATIONS:
- TYPE: Parent
  VALUE: SDOC-SSS-30
- TYPE: File
  VALUE: strictdoc/export/html/html_generator.py

[REQUIREMENT]
MID: 37399be2a8ac46889e3437209f9dffa9
UID: SDOC-SRS-50
STATUS: Active
TITLE: Web interface
STATEMENT: >>>
StrictDoc shall provide a web interface.
<<<
RELATIONS:
- TYPE: Parent
  VALUE: SDOC-SSS-31
- TYPE: Parent
  VALUE: DO178-6
- TYPE: Parent
  VALUE: SDOC-SSS-79
- TYPE: Parent
  VALUE: SDOC-SSS-80
- TYPE: File
  VALUE: strictdoc/server/app.py
- TYPE: File
  VALUE: strictdoc/server/routers/main_router.py

[REQUIREMENT]
MID: f97dc050ddab4a08bf1689200118faaa
UID: SDOC-SRS-123
STATUS: Active
TITLE: Multi-user editing of documents
STATEMENT: >>>
StrictDoc shall support concurrent use and editing of a single StrictDoc web
server instance by multiple users.
<<<
RELATIONS:
- TYPE: Parent
  VALUE: DO178-17
- TYPE: Parent
  VALUE: SDOC-SSS-81

[REQUIREMENT]
MID: 85960cfc3d83412185e5ce5ebd7c8976
UID: SDOC-SRS-208
STATUS: Active
TITLE: Field widgets
STATEMENT: >>>
StrictDoc's web interface shall provide widgets that insert and edit markup
elements, such as tables and links, in multiline text fields.
<<<
RATIONALE: >>>
A widget writes correct markup for the user. As a result, the user does not
need to remember the markup syntax or type every element by hand.
<<<
RELATIONS:
- TYPE: Parent
  VALUE: SDOC-SSS-80
- TYPE: File
  VALUE: strictdoc/export/html/_static/field_widgets.js

[REQUIREMENT]
MID: 8811f0ef33de4365bc66a602a8c184f6
UID: SDOC-SRS-48
STATUS: Active
TITLE: Preserve generated file names
STATEMENT: >>>
For all export operations, StrictDoc shall maintain the original filenames of
the documents when producing output files.
<<<
RATIONALE: >>>
Name preservation helps to visually identify which input file an output file
corresponds to.
<<<
RELATIONS:
- TYPE: Parent
  VALUE: SDOC-SSS-80

[[/SECTION]]

[[SECTION]]
MID: b99ebebdadb94fec968785429cef9002
UID: SECTION-SRS-Screen-Project-tree
TITLE: Screen: Project tree

[REQUIREMENT]
MID: 100fa410f4b443e69c48738899cfb5bd
UID: SDOC-SRS-53
STATUS: Active
TITLE: View project tree
STATEMENT: >>>
StrictDoc's "Project tree" screen shall provide browsing of a documentation
project tree.
<<<
RATIONALE: >>>
This screen is the main tool for visualizing the project tree structure.
<<<
RELATIONS:
- TYPE: Parent
  VALUE: SDOC-SSS-91

[REQUIREMENT]
MID: eb04abcfd64146f3b7be509afd1693f9
UID: SDOC-SRS-107
STATUS: Active
TITLE: Create document
STATEMENT: >>>
StrictDoc's Project Tree screen shall allow creating documents.
<<<
RELATIONS:
- TYPE: Parent
  VALUE: SDOC-SSS-3

[REQUIREMENT]
MID: de7cda1156e043d7999933a2df630a30
UID: SDOC-SRS-108
STATUS: Active
TITLE: Delete document
STATEMENT: >>>
StrictDoc's Project Tree screen shall allow deleting documents.
<<<
RELATIONS:
- TYPE: Parent
  VALUE: SDOC-SSS-3

[[/SECTION]]

[[SECTION]]
MID: 185cfc2d1ed4429ebaf0689f70a8cb0a
UID: SECTION-SRS-Screen-Document-DOC
TITLE: Screen: Document (DOC)

[REQUIREMENT]
MID: 93e6f08c949a48fa98cf86288492d8fd
UID: SDOC-SRS-201
STATUS: Active
TITLE: Format-specific document handling
STATEMENT: >>>
StrictDoc's Document screen shall arrange all CRUD operations according to the
input document format.

Example: If an SDoc document is read from a Markdown file using a dedicated
reader, it shall be written back using a Markdown writer.
<<<
RELATIONS:
- TYPE: Parent
  VALUE: SDOC-SSS-3

[REQUIREMENT]
MID: 9c962637ef7f45b6af6c83964b0a06d9
UID: SDOC-SRS-54
STATUS: Active
TITLE: Read document
STATEMENT: >>>
StrictDoc's Document screen shall allow reading documents.
<<<
RELATIONS:
- TYPE: Parent
  VALUE: SDOC-SSS-3

[REQUIREMENT]
MID: 201187122be14ea48d69106d396c6790
UID: SDOC-SRS-106
STATUS: Active
TITLE: Create node
STATEMENT: >>>
StrictDoc's Document screen shall allow creating document nodes.
<<<
RELATIONS:
- TYPE: Parent
  VALUE: SDOC-SSS-3

[REQUIREMENT]
MID: 9b291b5df5914f13b23fb8c367be0a24
UID: SDOC-SRS-161
STATUS: Active
TITLE: Clone node from existing node
STATEMENT: >>>
StrictDoc shall support cloning nodes from existing nodes.
<<<
RATIONALE: >>>
Simplifies the creation of similar nodes.
<<<

[REQUIREMENT]
MID: 13968ae160744e10ba8979eaee2f4f54
UID: SDOC-SRS-55
STATUS: Active
TITLE: Update node
STATEMENT: >>>
StrictDoc's Document screen shall allow update document content.
<<<
RELATIONS:
- TYPE: Parent
  VALUE: SDOC-SSS-4

[REQUIREMENT]
MID: 0ec87f08626a4839b5951d98fef9e0e1
UID: SDOC-SRS-162
STATUS: Active
TITLE: Delete node
STATEMENT: >>>
StrictDoc's Document screen shall support the deletion of document nodes.
<<<

[REQUIREMENT]
MID: b805e36294764e8f8cb5a88ab8fa0467
UID: SDOC-SRS-159
STATUS: Active
TITLE: Create node relation
STATEMENT: >>>
StrictDoc's Document screen shall creating updating node relations.
<<<
RELATIONS:
- TYPE: Parent
  VALUE: SDOC-SSS-7

[REQUIREMENT]
MID: f32c091454c94bc5bd2091e2c4f38582
UID: SDOC-SRS-158
STATUS: Active
TITLE: Update node relation
STATEMENT: >>>
StrictDoc's Document screen shall allow updating node relations.
<<<
RELATIONS:
- TYPE: Parent
  VALUE: SDOC-SSS-7

[REQUIREMENT]
MID: edc02a3a97704007b70b93102c76b278
UID: SDOC-SRS-92
STATUS: Active
TITLE: Move requirement / section nodes within document
STATEMENT: >>>
StrictDoc's Document screen shall provide a capability to move the nodes within
a document.
<<<
RATIONALE: >>>
Moving the nodes within a document is a convenience feature that speeds up the
requirements editing process significantly.
<<<
RELATIONS:
- TYPE: Parent
  VALUE: SDOC-SSS-5

[REQUIREMENT]
MID: 7a06d1433e4c4b0eaf55ede14507eac9
UID: SDOC-SRS-94
STATUS: Active
TITLE: Move requirement / section nodes between documents
STATEMENT: >>>
StrictDoc's Document screen shall provide a capability to move the nodes between
documents.
<<<
RATIONALE: >>>
Moving the nodes within a document is a convenience feature that speeds up the
requirements editing process significantly.
<<<
RELATIONS:
- TYPE: Parent
  VALUE: SDOC-SSS-70

[REQUIREMENT]
MID: 197e00dd3b1d42309250c89de23ea51b
UID: SDOC-SRS-56
STATUS: Active
TITLE: Edit Document grammar
STATEMENT: >>>
StrictDoc's screen shall allow editing a document's grammar.
<<<
RATIONALE: >>>
Editing document grammar allows a user to customize the requirements fields.
<<<
RELATIONS:
- TYPE: Parent
  VALUE: SDOC-SSS-62

[REQUIREMENT]
MID: 2706ac7ccb8148edb7b200a1b78c25d6
UID: SDOC-SRS-57
STATUS: Active
TITLE: Edit Document options
STATEMENT: >>>
StrictDoc's Document screen shall provide controls for configuring the
document-specific options.
<<<
RELATIONS:
- TYPE: Parent
  VALUE: SDOC-SSS-93

[REQUIREMENT]
MID: d64f7a0f6ba54672a62634304c54e2d4
UID: SDOC-SRS-96
STATUS: Active
TITLE: Auto-generate requirements UIDs
STATEMENT: >>>
StrictDoc's Document screen shall provide controls for automatic generation of
requirements UIDs.
<<<
RELATIONS:
- TYPE: Parent
  VALUE: SDOC-SSS-6
- TYPE: Parent
  VALUE: SDOC-SSS-80
- TYPE: File
  FORMAT: Sourcecode
  VALUE: strictdoc/core/analyzers/document_uid_analyzer.py
- TYPE: File
  FORMAT: Sourcecode
  VALUE: strictdoc/commands/manage_autouid_command.py

[REQUIREMENT]
MID: 956371b6a7824d0b91caa5603faeeae2
UID: SDOC-SRS-120
STATUS: Active
TITLE: Auto-completion for requirements UIDs
STATEMENT: >>>
StrictDoc's Document screen shall provide controls for automatic completion of
requirements UIDs.
<<<
COMMENT: >>>
The automatic completion can be especially useful when a user has to fill in a
parent relation UID.
<<<
RELATIONS:
- TYPE: Parent
  VALUE: SDOC-SSS-6
- TYPE: Parent
  VALUE: DO178-14
- TYPE: Parent
  VALUE: SDOC-SSS-80

[REQUIREMENT]
MID: 738b63b7f55b43eb99f5600bd65f5ba7
UID: SDOC-SRS-59
STATUS: Active
TITLE: Buttons to copy text to buffer
STATEMENT: >>>
StrictDoc shall provide a "copy text to buffer" button for all requirement's
text fields.
<<<
RELATIONS:
- TYPE: Parent
  VALUE: SDOC-SSS-80
- TYPE: File
  VALUE: strictdoc/export/html/_static/copy_to_clipboard.js

[REQUIREMENT]
MID: fa7fd8fd3a694d8e93953fd60e19fdde
UID: SDOC-SRS-61
STATUS: Active
TITLE: Tables HTML editor
STATEMENT: >>>
StrictDoc shall provide a solution for editing tables in its web interface.
<<<
RELATIONS:
- TYPE: Parent
  VALUE: SDOC-SSS-80
- TYPE: File
  VALUE: strictdoc/export/html/_static/table_editor.js

[[/SECTION]]

[[SECTION]]
MID: 2b5d74dafd6d43f4bab4c05ed4da6f0d
UID: SECTION-SRS-Screen-Table-TBL
TITLE: Screen: Table (TBL)

[REQUIREMENT]
MID: e12b4c5b4f13444d99279ab445df5bcc
UID: SDOC-SRS-62
STATUS: Active
TITLE: View TBL screen
STATEMENT: >>>
StrictDoc's Table screen shall allow reading documents in a table-like manner.
<<<
RELATIONS:
- TYPE: Parent
  VALUE: SDOC-SSS-73
- TYPE: File
  VALUE: strictdoc/export/html/generators/document_table.py

[[/SECTION]]

[[SECTION]]
MID: 3c589969eb6a41c19b1dd246dabadbc8
UID: SECTION-SRS-Screen-Traceability-TR
TITLE: Screen: Traceability (TR)

[REQUIREMENT]
MID: 35d4c1dd30814c2a80918a90081a88b7
UID: SDOC-SRS-65
STATUS: Active
TITLE: View TR screen
STATEMENT: >>>
StrictDoc shall provide a single document-level traceability screen.

NOTE: This screen helps to read a document like a normal document while the
traceability to this document's parent and child elements is visible at the same
time.
<<<
RELATIONS:
- TYPE: Parent
  VALUE: SDOC-SSS-28

[[/SECTION]]

[[SECTION]]
MID: 9d337068b6a940b7a98d40697ea200a8
UID: SECTION-SRS-Screen-Deep-traceability-DTR
TITLE: Screen: Deep traceability (DTR)

[REQUIREMENT]
MID: 48bc17d898c94605b17d0267480f57ee
UID: SDOC-SRS-66
STATUS: Active
TITLE: View DTR screen
STATEMENT: >>>
StrictDoc shall provide a deep traceability screen.
<<<
RELATIONS:
- TYPE: Parent
  VALUE: DO178-12

[[/SECTION]]

[[SECTION]]
MID: 181dfbcbbfac41e18f7fb09af0df8f4e
TITLE: Screen: HTML2PDF

[REQUIREMENT]
MID: f2fd90ad8a2946e7b085233a9c7a8a75
UID: SDOC-SRS-51
STATUS: Active
TITLE: Export to HTML content to PDF (HTML2PDF)
STATEMENT: >>>
StrictDoc shall allow exporting documents and entire documentation trees to PDF.
<<<
RATIONALE: >>>
As required by the parent requirement, PDF is one of the most common
documentation formats.
<<<
RELATIONS:
- TYPE: Parent
  VALUE: DO178-5
- TYPE: Parent
  VALUE: SDOC-SSS-96

[REQUIREMENT]
MID: 50eabada50be47a1938e55fc10814972
UID: SDOC-SRS-203
STATUS: Active
TITLE: Cross-linking PDF documents from same project tree
STATEMENT: >>>
When exporting multiple HTML documents from a same project tree into PDF,
StrictDoc shall preserve all cross-document linking in the output PDF documents.
<<<
RATIONALE: >>>
This enables navigation between PDF documents within the same project tree,
which can be useful for simplifying the review and tracing work performed by
readers.
<<<

[REQUIREMENT]
MID: 6cfcb21b3f1949f49d13af6b00d3d37a
UID: SDOC-SRS-160
STATUS: Active
TITLE: Custom PDF export template
STATEMENT: >>>
StrictDoc shall support the customization of the PDF export template.
<<<

[[/SECTION]]

[[SECTION]]
MID: ddf15b3113a54107979752ec192e2ded
TITLE: Screen: Project statistics

[REQUIREMENT]
MID: 19f7c2d35237423e950584a4a7aa95a7
UID: SDOC-SRS-97
STATUS: Active
TITLE: Display project statistics
STATEMENT: >>>
StrictDoc shall provide a Project Statistics screen that displays the following
project information:

- Project title
- Date of generation
- Git revision
- Total documents
- Total requirements
- Requirements status breakdown
- Total number of TBD/TBC found in documents.
<<<
RATIONALE: >>>
TBD
<<<
RELATIONS:
- TYPE: Parent
  VALUE: SDOC-SSS-49
- TYPE: Parent
  VALUE: DO178-12
- TYPE: Parent
  VALUE: SDOC-SSS-29

[REQUIREMENT]
MID: 7968fb7612f64504b5a430ccbffe80f1
UID: SDOC-SRS-154
STATUS: Active
TITLE: Support for user-provided custom statistics generators
STATEMENT: >>>
StrictDoc shall support customization of the project statistics screen, enabling
users to define and display their own project-specific statistics.
<<<
RATIONALE: >>>
Projects often have unique traceability and reporting requirements, and
supporting custom statistics allows StrictDoc to display metrics that are most
relevant to each project's context.
<<<
RELATIONS:
- TYPE: Parent
  VALUE: SDOC-SSS-49

[[/SECTION]]

[[SECTION]]
MID: d84e3a79b3e443cabe96d7c18ea5d322
TITLE: Screen: Document tree map

[REQUIREMENT]
MID: 1520fa85ed7a4f1aa80c49ed858f402f
UID: SDOC-SRS-157
STATUS: Active
TITLE: Tree map
STATEMENT: >>>
StrictDoc shall provide a tree map screen, visualizing the following
information:

- Document tree map
- Requirements coverage by source code
- Requirements coverage by test files.
<<<
RATIONALE: >>>
Enables the visualization and browsing of the overall document tree and
requirements coverage information.
<<<
RELATIONS:
- TYPE: Parent
  VALUE: SDOC-SSS-29

[[/SECTION]]

[[SECTION]]
MID: 63df985038374acb82e9b4185eff5a7e
TITLE: Screen: Source coverage

[REQUIREMENT]
MID: 3aeb1eea0dba4041a9161a1a8d291999
UID: SDOC-SRS-35
STATUS: Active
TITLE: Project source code coverage
STATEMENT: >>>
StrictDoc shall generate project source code coverage information.

NOTE: Source code information can be visualized using both web or CLI
interfaces.
<<<
RELATIONS:
- TYPE: Parent
  VALUE: SDOC-SSS-72
- TYPE: Parent
  VALUE: DO178-13

[[/SECTION]]

[[SECTION]]
MID: 9c19eea544ec4d90bb65fd8fd9b13cc4
TITLE: Screen: Single source file coverage

[REQUIREMENT]
MID: 56ecfb19152e45b09c0e55de2d1d5f05
UID: SDOC-SRS-36
STATUS: Active
TITLE: Single source file coverage
STATEMENT: >>>
StrictDoc shall generate single file traceability information.
<<<
RATIONALE: >>>
With this capability in place, it is possible to focus on a single
implementation file's links to requirements which helps in the code reviews and
inspections.
<<<
RELATIONS:
- TYPE: Parent
  VALUE: SDOC-SSS-72

[[/SECTION]]

[[SECTION]]
MID: 14ad600308434e6baaeef02d3e90b720
TITLE: Screen: Traceability matrix

[REQUIREMENT]
MID: 167f6fe66d7247a6bf628ed6c1949275
UID: SDOC-SRS-112
STATUS: Active
TITLE: Traceability matrix
STATEMENT: >>>
StrictDoc shall provide a traceability matrix screen.
<<<
RELATIONS:
- TYPE: Parent
  VALUE: SDOC-SSS-28
- TYPE: Parent
  VALUE: DO178-10
- TYPE: Parent
  VALUE: DO178-12

[[/SECTION]]

[[SECTION]]
MID: 544f8ffed8604e63a269a3f953681163
TITLE: Screen: Project tree diff

[REQUIREMENT]
MID: aef80cc1a3144564bf23bf3c2a1cfd7f
UID: SDOC-SRS-111
STATUS: Active
TITLE: Project tree diff
STATEMENT: >>>
StrictDoc shall provide a project tree diff screen.
<<<
RELATIONS:
- TYPE: Parent
  VALUE: SDOC-SSS-75
- TYPE: Parent
  VALUE: SDOC-SSS-74
- TYPE: Parent
  VALUE: DO178-15

[[/SECTION]]

[[SECTION]]
MID: 8380fb39beb04d1c9370733bcfafbc01
TITLE: Content search

[REQUIREMENT]
MID: 3e85dd6bf05a4cecb8e070fd81aa333a
UID: SDOC-SRS-155
STATUS: Active
TITLE: Content search
STATEMENT: >>>
StrictDoc shall provide searching documentation content with queries via a
search bar.
<<<
RATIONALE: >>>
As per the parent requirement, a search bar with query support enables users to
interactively find specific content without navigating the entire documentation
tree.
<<<
RELATIONS:
- TYPE: Parent
  VALUE: SDOC-SSS-95

[[/SECTION]]

[[/SECTION]]

[[SECTION]]
MID: 2d4dc6fc901f4b28aaf414fcfbdfabca
UID: SECTION-SRS-Requirements-to-source-traceability
TITLE: Requirements-to-source traceability

[REQUIREMENT]
MID: 221b544dab2e4b96be124e1caf84a7c2
UID: SDOC-SRS-33
STATUS: Active
TITLE: Link requirements with source files
STATEMENT: >>>
StrictDoc shall support bi-directional linking requirements with source files.
<<<
RELATIONS:
- TYPE: Parent
  VALUE: SDOC-SSS-72

[[SECTION]]
MID: 2f63252320d546d88462849b521f45ba
TITLE: Language-aware parsing of source code

[REQUIREMENT]
MID: 79a8080f6e41485f9835ccda067b34bc
UID: SDOC-SRS-142
TITLE: Language-aware parsing of source code
STATEMENT: >>>
StrictDoc shall support parsing the most commonly used formats and programming
languages to the Abstract Syntax Tree (AST) level.

The format examples: C, C++, Python, Rust, Ada, Robot, Gherkin, etc.
<<<
RATIONALE: >>>
StrictDoc must be capable of traversing the AST of common formats and
programming languages to identify and extract function and class markers.
<<<

[REQUIREMENT]
MID: 85a8080f8441485f9111ccda063b34bc
UID: SDOC-SRS-146
STATUS: Active
TITLE: Language-aware parsing of C/C++ code
STATEMENT: >>>
StrictDoc shall support parsing the C and C++ source files which includes:

- Recognizing functions and their Doxygen comments.
- Recognizing function declarations and function definitions.
<<<
RATIONALE: >>>
C and C++ languages are common languages for embedded and general systems
programming. These languages have to be handled with a dedicated parser because
of these languages' specifics.
<<<

[REQUIREMENT]
MID: 3456080f1358485f9bacdcda063b34bc
UID: SDOC-SRS-147
STATUS: Active
TITLE: Language-aware parsing of Python code
STATEMENT: >>>
StrictDoc shall support parsing the Python source files which includes:

- Recognizing Python functions, including nested functions.
- Recognizing Python classes, including nested classes.
- Recognizing decorated functions.
<<<
RATIONALE: >>>
Python language has to be handled with a dedicated parser because of this
language's specifics.
<<<

[REQUIREMENT]
MID: e71074247fbe47bfb5265f3bd631170f
UID: SDOC-SRS-204
STATUS: Active
TITLE: Language-aware parsing of Rust code
STATEMENT: >>>
StrictDoc shall support parsing the Rust source files.
<<<
RATIONALE: >>>
Rust language has to be handled with a dedicated parser because of this
language's specifics.
<<<

[REQUIREMENT]
MID: 9183080f1358485f9bacdcda0635109
UID: SDOC-SRS-148
STATUS: Active
TITLE: Language-aware parsing of Robot framework code
STATEMENT: >>>
StrictDoc shall support parsing the Robot framework test files.
<<<
RATIONALE: >>>
Robot framework's markup has to be handled with a dedicated parser because of
this language's specifics.
<<<

[[/SECTION]]

[REQUIREMENT]
MID: bdeda4b89d82446281e2c7c2eae46708
UID: SDOC-SRS-143
STATUS: Active
TITLE: Link requirements with test files and test reports
STATEMENT: >>>
StrictDoc shall support bi-directional linking between requirements, test files,
and test reports.
<<<
RATIONALE: >>>
Tracing requirements to not just test files but also the test report information
closes the verification cycle more completely.
<<<

[REQUIREMENT]
MID: aefeb5b89d82446281e2c7c2eae12345
UID: SDOC-SRS-144
STATUS: Active
TITLE: Link requirements with code coverage information
STATEMENT: >>>
StrictDoc shall support linking between requirements, source files, and code
coverage information.
<<<
RATIONALE: >>>
Tracing requirements to not just test files but also to the code coverage
information closes the verification cycle more completely.
<<<

[[SECTION]]
MID: 5fedbaba39d24da79d074501198ff654
TITLE: Forward linking from requirements to source code

[REQUIREMENT]
MID: 21637d9bec434d32bb6b97ba5a4e70e6
UID: SDOC-SRS-145
TITLE: SDoc markup's forward relations
STATEMENT: >>>
StrictDoc shall support forward linking from SDoc nodes to source files.
<<<
RATIONALE: >>>
There are cases when it is not possible to modify source code directly. The
forward linking enables to refer to the files or their parts from SDoc nodes.
Depending on a project structure, the forward linking from requirements to
source files can replace the backward linking from source code back to
requirements, or both approaches can co-exist.
<<<

[[/SECTION]]

[[SECTION]]
MID: 9c1dd6cbabd44ac680985c403cf710a7
TITLE: Source code markup – Relations

[REQUIREMENT]
MID: b9144222a7f3454da2989f494cd9647c
UID: SDOC-SRS-34
STATUS: Active
TITLE: Relation markers syntax
STATEMENT: >>>
StrictDoc shall support annotating source code with links that reference the
requirements.
<<<
RELATIONS:
- TYPE: Parent
  VALUE: SDOC-SSS-72
- TYPE: File
  FORMAT: Sourcecode
  VALUE: strictdoc/backend/sdoc_source_code/grammar.py
- TYPE: File
  FORMAT: Sourcecode
  VALUE: strictdoc/backend/sdoc_source_code/reader.py
- TYPE: File
  FORMAT: Sourcecode
  VALUE: strictdoc/backend/sdoc_source_code/models/range_marker.py
- TYPE: File
  FORMAT: Sourcecode
  VALUE: strictdoc/backend/sdoc_source_code/models/source_file_info.py

[REQUIREMENT]
MID: 61c25cab106e4283b2c6d64bf1db96b2
UID: SDOC-SRS-124
STATUS: Active
TITLE: Line marker
STATEMENT: >>>
StrictDoc's shall support line markers that can be attached to single source
code lines.

NOTE: A single-line marker points to a single line in a source file.
<<<
RATIONALE: >>>
Sometimes a requirement can influence only a single line in the source code. The
advantage of a single-line marker compared to a range marker is that a
single-line marker is not intrusive and does not clutter source code.
<<<
RELATIONS:
- TYPE: Parent
  VALUE: SDOC-SSS-72

[REQUIREMENT]
MID: 61c23c1b106e4583b2c6d64bf1d296ba
UID: SDOC-SRS-137
STATUS: Active
TITLE: Language element marker
STATEMENT: >>>
StrictDoc shall support relation markers that can be attached to individual
source code elements. StrictDoc shall support an optional scope attribute to
disambiguate the target element where StrictDoc can't infer it solely from the
marker position.

Note: The most basic example of such traceable elements are functions and
classes, but generally supported elements and available scope attributes depend
on the programming language.
<<<
RATIONALE: >>>
Source code elements can often be considered as the next level to trace from a
requirement. For example, a low level element is implemented by a function, or a
test case is implemented by a test function.

Sometimes it's also feasible to consider the source code elements as lean
replacement for prose requirement or test-case definitions.
<<<
RELATIONS:
- TYPE: Parent
  VALUE: SDOC-SSS-72

[REQUIREMENT]
MID: 82345cab106e4283b2c7774bf1db96b1
UID: SDOC-SRS-139
STATUS: Active
TITLE: File marker
STATEMENT: >>>
StrictDoc's shall support file markers that can be attached to entire source
files.
<<<
RATIONALE: >>>
There are cases when a requirement can be attached to an entire file.
<<<
RELATIONS:
- TYPE: Parent
  VALUE: SDOC-SSS-72

[REQUIREMENT]
MID: 11c23c1b105e4583b2c6d64bf1d296cc
UID: SDOC-SRS-138
STATUS: Active
TITLE: Range marker
STATEMENT: >>>
StrictDoc shall support relation markers that can be attached to source code
ranges.

NOTE: Compared to other marker types, to indicate a range, two markers are
needed: one to start a range and one to end a range.
<<<
RATIONALE: >>>
There are cases when a requirement implementation results in the requirement
affecting only a range/block of source code.
<<<
RELATIONS:
- TYPE: Parent
  VALUE: SDOC-SSS-72

[[/SECTION]]

[[SECTION]]
MID: 5ce2ea410dd94927807a258f482483a5
TITLE: Source code markup – Nodes

[REQUIREMENT]
MID: f44df3c6a84f4b4e9201a61023446d9c
UID: SDOC-SRS-141
STATUS: Active
TITLE: Parse nodes from source code
STATEMENT: >>>
StrictDoc shall support parsing nodes from source code.
<<<
RATIONALE: >>>
It can be practical to define the requirement and other nodes directly in source
comments and then let a requirements tool generate documents from these nodes'
content automatically.

A reference example: Generating test specifications from the TEST_SPEC nodes
which are defined directly in source code comments.
<<<

[[/SECTION]]

[[/SECTION]]

[[SECTION]]
MID: 1acdd6ddf9d24dbaa320230402152226
UID: SECTION-SRS-Export-import-formats
TITLE: Export/import formats

[[SECTION]]
MID: ce1d174a4d794250931a5ba519583be6
UID: SECTION-SRS-RST
TITLE: RST

[REQUIREMENT]
MID: 2aa615b9cf264e7aad826f4ff466e514
UID: SDOC-SRS-70
STATUS: Active
TITLE: Export to RST
STATEMENT: >>>
StrictDoc shall allow exporting SDoc content to the RST format.
<<<
RATIONALE: >>>
Exporting SDoc content to RST enables:

1) Generating RST to Sphinx HTML documentation.
2) Generating RST to PDF using Sphinx/LaTeX.
<<<
RELATIONS:
- TYPE: Parent
  VALUE: DO178-5
- TYPE: Parent
  VALUE: DO178-16

[REQUIREMENT]
MID: 6faffbd1d4cc47ea88c08ef38966e5ec
UID: SDOC-SRS-71
STATUS: Active
TITLE: Docutils
STATEMENT: >>>
StrictDoc shall generate RST markup to HTML using Docutils.
<<<
RATIONALE: >>>
Docutils is the most mature RST-to-HTML converter.
<<<
COMMENT: >>>
TBD: Move this to design decisions.
<<<
RELATIONS:
- TYPE: Parent
  VALUE: DO178-5
- TYPE: Parent
  VALUE: DO178-16

[[/SECTION]]

[[SECTION]]
MID: a906dfb776334b8985f778f0fe1b79e4
UID: SECTION-SRS-ReqIF
TITLE: ReqIF

[REQUIREMENT]
MID: 2bf94015818e4770b2b1947b5fdbb969
UID: SDOC-SRS-72
STATUS: Active
TITLE: Export/import from/to ReqIF
STATEMENT: >>>
StrictDoc shall support exporting/importing requirements content from/to ReqIF
format.
<<<
RELATIONS:
- TYPE: Parent
  VALUE: SDOC-SSS-58

[REQUIREMENT]
MID: bb52b698d7a544aca420d606e4e51356
UID: SDOC-SRS-73
STATUS: Active
TITLE: Standalone ReqIF layer
STATEMENT: >>>
StrictDoc shall maintain the core ReqIF implementation as a separate software
component.
<<<
RATIONALE: >>>
ReqIF is a well-defined standard which exists independently of StrictDoc's
development. It is reasonable to maintain the ReqIF codebase as a separate
software component to allow independent development and easier maintainability.
<<<
RELATIONS:
- TYPE: Parent
  VALUE: SDOC-SSS-90

[[/SECTION]]

[[SECTION]]
MID: 0ffda51372b641f6ba460bf5ac8b3627
UID: SECTION-SRS-Excel
TITLE: Excel and CSV

[REQUIREMENT]
MID: f7b587f66dda402dbd58768e2740742f
UID: SDOC-SRS-74
STATUS: Active
TITLE: Export to Excel
STATEMENT: >>>
StrictDoc shall allow exporting SDoc documents to Excel, one Excel sheet per
document.
<<<
RELATIONS:
- TYPE: Parent
  VALUE: SDOC-SSS-60
- TYPE: File
  FORMAT: Sourcecode
  VALUE: strictdoc/backend/excel/export/excel_generator.py
- TYPE: File
  FORMAT: Sourcecode
  VALUE: tests/integration/features/excel/export/20_excel_export_multiple_docs/test.itest

[REQUIREMENT]
MID: 97b587f66dda402dbd58768e2740742f
UID: SDOC-SRS-152
STATUS: Active
TITLE: Import from Excel
STATEMENT: >>>
StrictDoc shall allow importing Excel documents to SDoc documents, one Excel
sheet per document.
<<<
RELATIONS:
- TYPE: Parent
  VALUE: SDOC-SSS-60
- TYPE: File
  FORMAT: Sourcecode
  VALUE: strictdoc/backend/excel/export/excel_generator.py
- TYPE: File
  FORMAT: Sourcecode
  VALUE: tests/integration/features/excel/export/20_excel_export_multiple_docs/test.itest

[REQUIREMENT]
MID: 5aa75848972249d5bec8a40812b99d86
UID: SDOC-SRS-134
STATUS: Active
TITLE: Selected fields export
STATEMENT: >>>
StrictDoc Excel export shall allow exporting SDoc documents to Excel with only
selected fields.
<<<
RELATIONS:
- TYPE: Parent
  VALUE: SDOC-SSS-60
- TYPE: File
  VALUE: tests/integration/features/excel/export/03_custom_fields_to_export/test.itest

[[/SECTION]]

[[/SECTION]]

[[SECTION]]
MID: 53cfa6296eec45479544e6c5165d7fb9
UID: SECTION-SRS-Command-line-interface
TITLE: Command-line interface

[[SECTION]]
MID: 63373c3875404f1c820add84ea057c73
TITLE: General CLI requirements

[REQUIREMENT]
MID: 598647eed3a446fe93e2c54b197f830e
UID: SDOC-SRS-103
STATUS: Active
TITLE: Command-line interface
STATEMENT: >>>
StrictDoc shall provide a command-line interface.
<<<
RELATIONS:
- TYPE: Parent
  VALUE: SDOC-SSS-32
- TYPE: File
  FORMAT: Sourcecode
  VALUE: strictdoc/cli/main.py
- TYPE: File
  FORMAT: Sourcecode
  VALUE: strictdoc/cli/cli_arg_parser.py

[[/SECTION]]

[[SECTION]]
MID: 7c6a0efe76b84dcd842ef371796e787e
UID: SECTION-SRS-Command-Manage
TITLE: Command: Manage

[[SECTION]]
MID: bea76afe9bf241eaaf5984b54e00ff76
UID: SECTION-SRS-Command-Auto-UID
TITLE: Command: Auto UID

[REQUIREMENT]
MID: 7daa1310876a421f8e39f8ac25b99c1d
UID: SDOC-SRS-85
STATUS: Active
TITLE: Auto-generate requirements UIDs
STATEMENT: >>>
StrictDoc shall allow automatic generation of requirements UIDs.
<<<
RELATIONS:
- TYPE: Parent
  VALUE: SDOC-SSS-6

[[/SECTION]]

[[/SECTION]]

[[/SECTION]]

[[SECTION]]
MID: a0ed7cdd06ec4f0ab6d3ba56cced8c7e
TITLE: Python API

[REQUIREMENT]
MID: a20c5b6a021f4dd5a5a5dda2880c1b87
UID: SDOC-SRS-125
STATUS: Active
TITLE: StrictDoc Python API
STATEMENT: >>>
StrictDoc shall provide a Python API for its core functions:

- Reading SDoc files
- Creating traceability graph
- Generating HTML exports
- Converting SDoc to other formats.
<<<
RELATIONS:
- TYPE: Parent
  VALUE: SDOC-SSS-79
- TYPE: Parent
  VALUE: SDOC-SSS-86
- TYPE: Parent
  VALUE: SDOC-SSS-87

[[/SECTION]]

[[SECTION]]
MID: 590121ded2074757aa1720b4d8013426
TITLE: Web server

[REQUIREMENT]
MID: 409f462f1f4645c8ad24980727a72521
UID: SDOC-SRS-126
STATUS: Active
TITLE: Web server
STATEMENT: >>>
StrictDoc shall provide a web server.
<<<
RATIONALE: >>>
A web server is a precondition for StrictDoc's web interface. A web server can
be available to a single user on their local machine or it can be deployed to a
network and be made accessible by several computers.
<<<
RELATIONS:
- TYPE: Parent
  VALUE: SDOC-SSS-83

[[/SECTION]]

[[SECTION]]
MID: 44eb09d0e5b542d5984d234167e6f337
TITLE: User experience

[REQUIREMENT]
MID: 2bfb3703b218411b87864733bffb59cf
UID: SDOC-SRS-163
STATUS: Active
TITLE: StrictDoc identification
STATEMENT: >>>
StrictDoc shall provide 'about' and 'version' commands that display the
project's title, current version, license, and links to the project's web pages.
<<<
RELATIONS:
- TYPE: Parent
  VALUE: SDOC-SSS-97

[[SECTION]]
MID: 821c01118a9643a188a4ecc5b0cec6a5
UID: SECTION-SSRS-Strict-mode-by-default
TITLE: Strict mode by default

[REQUIREMENT]
MID: c4e9dce647654deeab8471d04573f8cb
UID: SDOC-SRS-6
STATUS: Active
TITLE: Warnings are errors
STATEMENT: >>>
StrictDoc's default mode of operation shall treat all warnings as errors.
<<<
RATIONALE: >>>
When warnings are treated as errors, the user becomes aware of potential issues
as soon as they appear.
<<<
RELATIONS:
- TYPE: Parent
  VALUE: SDOC-SSS-78

[[/SECTION]]

[[/SECTION]]

[[SECTION]]
MID: 40e7bd8aabdf4cb889e9d7b01b8729e6
UID: SECTION-SRS-Configurability
TITLE: Configurability

[REQUIREMENT]
MID: 8777318f4a5b481596ac1f43e73b24c9
UID: SDOC-SRS-205
STATUS: Active
TITLE: Python configuration file
STATEMENT: >>>
StrictDoc shall allow configuration of projects settings using a Python file.
<<<
RELATIONS:
- TYPE: Parent
  VALUE: SDOC-SSS-92

[REQUIREMENT]
MID: a6e70c0619204a26b135d1e5fca45dd7
UID: SDOC-SRS-39
STATUS: Active
TITLE: Feature toggles
STATEMENT: >>>
StrictDoc shall allow a user to select a subset of StrictDoc's available
features by listing them in the Python configuration file.
<<<
RELATIONS:
- TYPE: Parent
  VALUE: SDOC-SSS-92

[REQUIREMENT]
MID: a8a17295d3e24601891c7d19d5ca67d9
UID: SDOC-SRS-119
STATUS: Active
TITLE: 'Host' parameter
STATEMENT: >>>
StrictDoc shall support configuring a host/port on which the StrictDoc web
server is run.
<<<
RELATIONS:
- TYPE: Parent
  VALUE: DO178-8

[[/SECTION]]

[[SECTION]]
MID: bb14fb2c46f34cf1a82b417b57e95853
UID: SECTION-SSRS-Performance
TITLE: Performance

[REQUIREMENT]
MID: acd97ca6b9d2451da53168917d96705e
UID: SDOC-SRS-1
STATUS: Active
TITLE: Process-based parallelization
STATEMENT: >>>
StrictDoc shall support process-based parallelization for time-critical tasks.
<<<
RATIONALE: >>>
Process-based parallelization can provide a good speed-up when several large
documents have to be generated.
<<<
RELATIONS:
- TYPE: Parent
  VALUE: SDOC-SSS-13
- TYPE: Parent
  VALUE: SDOC-SSS-14

[REQUIREMENT]
MID: 54602f6d120548c8bbd70d1d25113d53
UID: SDOC-SRS-95
STATUS: Active
TITLE: Caching of parsed SDoc documents
STATEMENT: >>>
StrictDoc shall implement caching of parsed SDoc documents.
<<<
RELATIONS:
- TYPE: Parent
  VALUE: SDOC-SSS-13
- TYPE: Parent
  VALUE: SDOC-SSS-14

[REQUIREMENT]
MID: 6fec2f8c0baa4ddba95bee05ad03a785
UID: SDOC-SRS-2
STATUS: Active
TITLE: Incremental generation of documents
STATEMENT: >>>
StrictDoc shall support incremental generation of documents.

NOTE: "Incremental" means that only the modified documents are regenerated when
StrictDoc is run repeatedly against the same project tree.
<<<
RELATIONS:
- TYPE: Parent
  VALUE: SDOC-SSS-13
- TYPE: Parent
  VALUE: SDOC-SSS-14

[REQUIREMENT]
MID: 5f2df631605543d18d57e09bc3791003
UID: SDOC-SRS-3
STATUS: Active
TITLE: Caching of RST fragments
STATEMENT: >>>
StrictDoc shall cache the RST fragments rendered to HTML.
<<<
RATIONALE: >>>
Conversion of RST markup to HTML is a time consuming process. Caching the
rendered HTML of each fragment helps to save time when rendering the HTML
content.
<<<
RELATIONS:
- TYPE: Parent
  VALUE: SDOC-SSS-13
- TYPE: Parent
  VALUE: SDOC-SSS-14

[REQUIREMENT]
MID: d0c4828ed8434613aae844481bbef1ca
UID: SDOC-SRS-4
STATUS: Active
TITLE: On-demand loading of HTML pages
STATEMENT: >>>
StrictDoc's web interface shall generate the HTML content only when it is
directly requested by a user.
<<<
RATIONALE: >>>
Generating a whole documentation tree for a user project can be time consuming.
The on-demand loading ensures the "do less work" approach when it comes to
rendering the HTML pages.
<<<
RELATIONS:
- TYPE: Parent
  VALUE: SDOC-SSS-13
- TYPE: Parent
  VALUE: SDOC-SSS-14

[REQUIREMENT]
MID: 4e014d3291ce460c993a0ff334eff4a7
UID: SDOC-SRS-5
STATUS: Active
TITLE: Precompiled Jinja templates
STATEMENT: >>>
StrictDoc shall support a precompilation of HTML templates.
<<<
RATIONALE: >>>
The StrictDoc-exported HTML content visible to a user is assembled from numerous
small HTML fragments. Precompiling the HTML templates from which the content
gets rendered improves the performance of the HTML rendering.
<<<
RELATIONS:
- TYPE: Parent
  VALUE: SDOC-SSS-13
- TYPE: Parent
  VALUE: SDOC-SSS-14
- TYPE: File
  FORMAT: Sourcecode
  VALUE: strictdoc/export/html/html_templates.py

[[/SECTION]]

[[SECTION]]
MID: de3a4de44f474784bf233ea7610eac6c
UID: SECTION-SRS-Quality-requirements
TITLE: Development process requirements

[[SECTION]]
MID: cbee3d3e8a9d440abaa58387c342602c
TITLE: General process

[REQUIREMENT]
MID: 27319e3866b8423099774d8770950acd
UID: SDOC-SRS-133
STATUS: Active
TITLE: Priority handling of critical issues in StrictDoc
STATEMENT: >>>
All critical issues reported in relation to StrictDoc shall be addressed with
utmost priority.
<<<
RATIONALE: >>>
Prioritizing major issues ensures StrictDoc remains stable and reliable,
preventing serious problems that could compromise its performance and integrity.
<<<
RELATIONS:
- TYPE: Parent
  VALUE: SDOC-SSS-78

[[/SECTION]]

[[SECTION]]
MID: 47cec130eb3d4583825355f2635e7011
UID: SECTION-SRS-Requirements-engineering
TITLE: Requirements engineering

[REQUIREMENT]
MID: d0ab977bbb494cbf818c92a1cab1bef0
UID: SDOC-SRS-128
STATUS: Active
TITLE: Requirements-based development
STATEMENT: >>>
StrictDoc's development shall be requirements-based.
<<<
RELATIONS:
- TYPE: Parent
  VALUE: SDOC-SSS-78
- TYPE: Parent
  VALUE: SDOC-SSS-76

[REQUIREMENT]
MID: b3fff332c2e342ec9dd372ebd49cb64d
UID: SDOC-SRS-91
STATUS: Active
TITLE: Self-hosted requirements
STATEMENT: >>>
StrictDoc's requirements shall be written using StrictDoc.
<<<
RELATIONS:
- TYPE: Parent
  VALUE: SDOC-SSS-50
- TYPE: Parent
  VALUE: SDOC-SSS-78

[[/SECTION]]

[[SECTION]]
MID: dfbaabc0529f4cc987358ae0563910e9
UID: SECTION-SRS-Implementation-requirements
TITLE: Implementation requirements

[[SECTION]]
MID: 5eb734a4b8944531aa75f0b71ef22d52
UID: SECTION-SRS-Programming-languages
TITLE: Programming languages

[REQUIREMENT]
MID: 4053ea6c8f6c4c29b89fea0e39912861
UID: SDOC-SRS-8
STATUS: Active
TITLE: Python language
STATEMENT: >>>
StrictDoc shall be written in Python.
<<<
RATIONALE: >>>
Python has an excellent package ecosystem. It is a widely used language. It is
most often the next language for C/C++ programming community when it comes to
the tools development and scripting tasks.
<<<
RELATIONS:
- TYPE: Parent
  VALUE: SDOC-SSS-69

[[/SECTION]]

[[SECTION]]
MID: 131af6457a9f43299306e6dc9fce65a7
UID: SECTION-SRS-Cross-platform-availability
TITLE: Cross-platform availability

[REQUIREMENT]
MID: ceee07bdc9bd42fc9a4d0e9b4bfc312f
UID: SDOC-SRS-9
STATUS: Active
TITLE: Linux
STATEMENT: >>>
StrictDoc shall support the Linux operating systems.
<<<
RELATIONS:
- TYPE: Parent
  VALUE: SDOC-SSS-67

[REQUIREMENT]
MID: f8c7586e1b324480ac0bd153e068350d
UID: SDOC-SRS-10
STATUS: Active
TITLE: macOS
STATEMENT: >>>
StrictDoc shall support the macOS operating system.
<<<
RELATIONS:
- TYPE: Parent
  VALUE: SDOC-SSS-67

[REQUIREMENT]
MID: 6af3dbb1e05244579622d3d2a26b5413
UID: SDOC-SRS-11
STATUS: Active
TITLE: Windows
STATEMENT: >>>
StrictDoc shall support the Windows operating system.
<<<
RELATIONS:
- TYPE: Parent
  VALUE: SDOC-SSS-67

[[/SECTION]]

[[/SECTION]]

[[SECTION]]
MID: 852396c217184ba98a0d26b92f36fd04
UID: SECTION-SRS-Implementation-constraints
TITLE: Implementation constraints

[REQUIREMENT]
MID: 83d5c896004948b48c3597d58267dafa
UID: SDOC-SRS-89
STATUS: Active
TITLE: Use of open source components
STATEMENT: >>>
StrictDoc shall be built using only open source software components.
<<<
RATIONALE: >>>
No commercial/proprietary dependency chain ensures that StrictDoc remain free
and open for everyone.
<<<
RELATIONS:
- TYPE: Parent
  VALUE: DO178-7
- TYPE: Parent
  VALUE: SDOC-SSS-39
- TYPE: File
  VALUE: pyproject.toml

[REQUIREMENT]
MID: b22bf982e73246a79a5ba4ae653d21e5
UID: SDOC-SRS-14
STATUS: Active
TITLE: No heavy UI frameworks
STATEMENT: >>>
StrictDoc shall avoid using large and demanding UI frameworks.

NOTE: An example of frameworks that require a very specific architecture: React
JS, AngularJS.
<<<
RELATIONS:
- TYPE: Parent
  VALUE: SDOC-SSS-90

[REQUIREMENT]
MID: 309e4108c1fa47e99d4331af642f3b81
UID: SDOC-SRS-15
STATUS: Active
TITLE: No use of NPM
STATEMENT: >>>
StrictDoc shall avoid extending its infrastructure with anything based on
NPM-ecosystem.
<<<
RATIONALE: >>>
StrictDoc already deals with the Python/Pip/Pypi ecosystem. The amount of
necessary maintenance is already quite high. NPM is known for splitting its
projects into very small parts, which increases the complexity of maintaining
all dependencies.
<<<
RELATIONS:
- TYPE: Parent
  VALUE: SDOC-SSS-90

[REQUIREMENT]
MID: b9cacb97a045418385c7f870b23ac063
UID: SDOC-SRS-16
STATUS: Active
TITLE: No use of JavaScript replacement languages (e.g., Typescript)
STATEMENT: >>>
StrictDoc shall avoid using JavaScript-based programming languages.
<<<
RATIONALE: >>>
The development team does not have specific experience with any of the JS
alternatives. Staying with a general subset of JavaScript is a safer choice.
<<<
RELATIONS:
- TYPE: Parent
  VALUE: SDOC-SSS-90

[REQUIREMENT]
MID: 70f05a744a0546909dc5b69de88ad41f
UID: SDOC-SRS-87
STATUS: Active
TITLE: Monolithic application with no microservices
STATEMENT: >>>
StrictDoc shall avoid using microservices and microservice-based architectures.
<<<
RATIONALE: >>>
The project is too small to scale to a multi-service architecture.
<<<
COMMENT: >>>
This requirement could be re-considered only if a significant technical pressure
would require the use of microservices.
<<<
RELATIONS:
- TYPE: Parent
  VALUE: SDOC-SSS-82

[REQUIREMENT]
MID: 7d68821750a54cb5833b608cfc278f47
UID: SDOC-SRS-88
STATUS: Active
TITLE: No reliance on containerization
STATEMENT: >>>
StrictDoc shall avoid using containers and containerization technologies.
<<<
RATIONALE: >>>
Containers are significant extra layer of complexity. They are hard to debug.
<<<
COMMENT: >>>
This constraint does not block a StrictDoc user from wrapping StrictDoc into
their containers.
<<<
RELATIONS:
- TYPE: Parent
  VALUE: SDOC-SSS-82

[[/SECTION]]

[[SECTION]]
MID: e4e5b9934e074cdb9567fa197db20a4a
UID: SECTION-SRS-Coding-constraints
TITLE: Coding constraints

[REQUIREMENT]
MID: 61d96cd1d03e40c48187ee67ac0b65f6
UID: SDOC-SRS-40
STATUS: Active
TITLE: Use of asserts
STATEMENT: >>>
StrictDoc's development shall ensure a use of assertions throughout the project
codebase.

NOTE: At a minimum, the function input parameters must be checked for validity.
<<<
RELATIONS:
- TYPE: Parent
  VALUE: SDOC-SSS-78

[REQUIREMENT]
MID: 72b5b0c925cf4ef49749b7e466675df1
UID: SDOC-SRS-41
STATUS: Active
TITLE: Use of type annotations in Python code
STATEMENT: >>>
StrictDoc's development shall ensure a use of type annotations throughout the
project's Python codebase.
<<<
RELATIONS:
- TYPE: Parent
  VALUE: SDOC-SSS-78

[[/SECTION]]

[[SECTION]]
MID: 61e87567580045378d970b327d218cac
UID: SECTION-SRS-Linting
TITLE: Linting

[REQUIREMENT]
MID: 6c0163c56ade49faa353ec06cbd676cd
UID: SDOC-SRS-42
STATUS: Active
TITLE: Compliance with Python community practices (PEP8 etc)
STATEMENT: >>>
StrictDoc's development shall ensure that the project's codebase is compliant
with the Python community's modern practices.
<<<
RELATIONS:
- TYPE: Parent
  VALUE: SDOC-SSS-90

[[/SECTION]]

[[SECTION]]
MID: 3029f97a1276499dbbd5d7c71691908e
UID: SECTION-SRS-Static-analysis
TITLE: Static analysis

[REQUIREMENT]
MID: 2cc9b494ca6248058b6bf63b6e2c1cfa
UID: SDOC-SRS-43
STATUS: Active
TITLE: Static type checking
STATEMENT: >>>
StrictDoc's development shall include a continuous type checking of StrictDoc's
codebase.
<<<
RELATIONS:
- TYPE: Parent
  VALUE: SDOC-SSS-78
- TYPE: File
  VALUE: tasks.py

[[/SECTION]]

[[SECTION]]
MID: 3aba8ca86d404ba9a063ce125489f35b
UID: SECTION-SRS-Testing
TITLE: Testing

[REQUIREMENT]
MID: 2731c64ab32146eeb4b8167df4a34540
UID: SDOC-SRS-44
STATUS: Active
TITLE: Unit testing
STATEMENT: >>>
StrictDoc's development shall provide unit testing of its codebase.
<<<
RELATIONS:
- TYPE: Parent
  VALUE: SDOC-SSS-77
- TYPE: Parent
  VALUE: SDOC-SSS-78

[REQUIREMENT]
MID: 70ef3986cfc4437bbb10288d3b55958c
UID: SDOC-SRS-45
STATUS: Active
TITLE: CLI interface black-box integration testing
STATEMENT: >>>
StrictDoc's development shall provide complete black-box integration testing of
its command-line interface.
<<<
RELATIONS:
- TYPE: Parent
  VALUE: SDOC-SSS-77
- TYPE: Parent
  VALUE: SDOC-SSS-78

[REQUIREMENT]
MID: a42c65f1a53b4c9bb50bc2a1ecb855cb
UID: SDOC-SRS-46
STATUS: Active
TITLE: Web end-to-end testing
STATEMENT: >>>
StrictDoc's development shall provide complete end-to-end testing of the web
interface.
<<<
RELATIONS:
- TYPE: Parent
  VALUE: SDOC-SSS-77
- TYPE: Parent
  VALUE: SDOC-SSS-78

[REQUIREMENT]
MID: c90f35ab9a7f4c29a418557151878b9f
UID: SDOC-SRS-47
STATUS: Active
TITLE: At least one integration or end-to-end test
STATEMENT: >>>
Every update to the StrictDoc codebase shall be complemented with a
corresponding provision of at least one test as follows:

- For web interface: at least one end-to-end test.
- For command-line interface: at least one black-box integration test.
- For internal Python functions: at least one unit test.

NOTE: This requirement implies that no modifications to StrictDoc's
functionality can be merged unless accompanied by at least one test.
<<<
RATIONALE: >>>
This requirement ensures that every new feature or a chance in the codebase is
covered/stressed by at least one test, according to the change type.
<<<
RELATIONS:
- TYPE: Parent
  VALUE: SDOC-SSS-77
- TYPE: Parent
  VALUE: SDOC-SSS-78

[[/SECTION]]

[[/SECTION]]

[[SECTION]]
MID: 83bdb9731e78431cb48d584d279443b4
TITLE: Code hosting and distribution

[[SECTION]]
MID: dbd186fae9624fd6af8aeb55edfaa43b
UID: SECTION-SRS-Code-hosting
TITLE: Code hosting

[REQUIREMENT]
MID: b112c60bc2f34114ab1f3361a1a10a00
UID: SDOC-SRS-12
STATUS: Active
TITLE: GitHub
STATEMENT: >>>
StrictDoc's source code shall be hosted on GitHub.
<<<
RELATIONS:
- TYPE: Parent
  VALUE: SDOC-SSS-38
- TYPE: Parent
  VALUE: SDOC-SSS-82

[[/SECTION]]

[REQUIREMENT]
MID: bd949cbbe07c4cb29492ea0c8e5c1eec
UID: SDOC-SRS-118
STATUS: Active
TITLE: StrictDoc license
STATEMENT: >>>
All StrictDoc software shall be licensed under the Apache 2 license.
<<<
RELATIONS:
- TYPE: Parent
  VALUE: SDOC-SSS-40
- TYPE: File
  VALUE: LICENSE
- TYPE: File
  VALUE: NOTICE

[[/SECTION]]
