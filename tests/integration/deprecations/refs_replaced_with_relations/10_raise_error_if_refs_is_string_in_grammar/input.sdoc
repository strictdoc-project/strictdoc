[DOCUMENT]
TITLE: Hello world doc

[GRAMMAR]
ELEMENTS:
- TAG: REQUIREMENT
  FIELDS:
  - TITLE: UID
    TYPE: String
    REQUIRED: False
  - TITLE: REFS
    TYPE: String
    REQUIRED: False
  - TITLE: STATEMENT
    TYPE: String
    REQUIRED: True

[REQUIREMENT]
UID: REQ-1
STATEMENT: Shall do 1.

[REQUIREMENT]
UID: REQ-2
REFS:
- TYPE: Parent
  VALUE: REQ-1
STATEMENT: Shall do 1.
