[DOCUMENT]
TITLE: Document with one section and one requirement

[SECTION]
TITLE: Section #1

[REQUIREMENT]
UID: LLR001
STATEMENT: >>>
The mapping function shall map requirement_ID to UID.
<<<

[/SECTION]
