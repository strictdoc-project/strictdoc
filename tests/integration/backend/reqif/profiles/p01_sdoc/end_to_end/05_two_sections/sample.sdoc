[DOCUMENT]
TITLE: sample

[GRAMMAR]
ELEMENTS:
- TAG: REQUIREMENT
  FIELDS:
  - TITLE: UID
    TYPE: String
    REQUIRED: False
  - TITLE: LEVEL
    TYPE: String
    REQUIRED: False
  - TITLE: STATUS
    TYPE: String
    REQUIRED: False
  - TITLE: TAGS
    TYPE: String
    REQUIRED: False
  - TITLE: TITLE
    TYPE: String
    REQUIRED: False
  - TITLE: STATEMENT
    TYPE: String
    REQUIRED: False
  - TITLE: RATIONALE
    TYPE: String
    REQUIRED: False
  - TITLE: COMMENT
    TYPE: String
    REQUIRED: False
  RELATIONS:
  - TYPE: Parent
  - TYPE: File

[SECTION]
TITLE: Section #1

[REQUIREMENT]
UID: REQ-1
STATEMENT: >>>
The mapping function shall map requirement_ID to UID.
<<<

[/SECTION]

[SECTION]
TITLE: Section #2

[REQUIREMENT]
UID: REQ-2
STATEMENT: >>>
The mapping function shall map requirement_ID to UID.
<<<

[/SECTION]
