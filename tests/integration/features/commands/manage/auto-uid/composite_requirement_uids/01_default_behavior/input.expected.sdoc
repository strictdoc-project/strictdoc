[DOCUMENT]
TITLE: Hello world doc

[GRAMMAR]
ELEMENTS:
- TAG: SECTION
  PROPERTIES:
    IS_COMPOSITE: True
  FIELDS:
  - TITLE: UID
    TYPE: String
    REQUIRED: False
  - TITLE: LEVEL
    TYPE: String
    REQUIRED: False
  - TITLE: PREFIX
    TYPE: String
    REQUIRED: False
  - TITLE: TITLE
    TYPE: String
    REQUIRED: True
- TAG: TEXT
  FIELDS:
  - TITLE: UID
    TYPE: String
    REQUIRED: False
  - TITLE: STATEMENT
    TYPE: String
    REQUIRED: True
- TAG: COMPOSITE_REQUIREMENT
  PROPERTIES:
    IS_COMPOSITE: True
  FIELDS:
  - TITLE: MID
    TYPE: String
    REQUIRED: False
  - TITLE: UID
    TYPE: String
    REQUIRED: False
  - TITLE: STATEMENT
    TYPE: String
    REQUIRED: False
- TAG: REQUIREMENT
  FIELDS:
  - TITLE: MID
    TYPE: String
    REQUIRED: False
  - TITLE: UID
    TYPE: String
    REQUIRED: False
  - TITLE: STATEMENT
    TYPE: String
    REQUIRED: False

[[COMPOSITE_REQUIREMENT]]
UID: REQ-1
STATEMENT: System shall do 1.

[REQUIREMENT]
UID: REQ-2
STATEMENT: System shall do 1.

[[/COMPOSITE_REQUIREMENT]]

[[COMPOSITE_REQUIREMENT]]
UID: REQ-3
STATEMENT: System shall do 2.

[REQUIREMENT]
UID: REQ-4
STATEMENT: System shall do 2.

[[/COMPOSITE_REQUIREMENT]]

[[COMPOSITE_REQUIREMENT]]
UID: REQ-5
STATEMENT: System shall do 3.

[REQUIREMENT]
UID: REQ-6
STATEMENT: System shall do 3.

[[/COMPOSITE_REQUIREMENT]]
