[DOCUMENT]
TITLE: Document 1

[REQUIREMENT]
TITLE: Requirement title
STATEMENT: >>>
Requirement statement.
<<<
RATIONALE: >>>
Requirement rationale.
<<<

[REQUIREMENT]
UID: REQ-1
STATEMENT: >>>
Shall do.
<<<
