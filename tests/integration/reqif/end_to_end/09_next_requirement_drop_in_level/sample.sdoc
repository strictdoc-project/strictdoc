[DOCUMENT]
TITLE: Document with two nested sections

[SECTION]
TITLE: Section #1

[SECTION]
TITLE: Section #1.1

[REQUIREMENT]
UID: REQ-1.1.1
STATEMENT: The mapping function shall map requirement_ID to UID.

[/SECTION]

[REQUIREMENT]
UID: REQ-1.2.1
STATEMENT: The mapping function shall map requirement_ID to UID.

[/SECTION]
