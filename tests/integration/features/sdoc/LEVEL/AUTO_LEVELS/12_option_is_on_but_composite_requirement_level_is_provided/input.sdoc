[DOCUMENT]
TITLE: Hello world doc
OPTIONS:
  AUTO_LEVELS: On

[GRAMMAR]
ELEMENTS:
- TAG: SECTION
  PROPERTIES:
    IS_COMPOSITE: True
    PREFIX: None
  FIELDS:
  - TITLE: MID
    TYPE: String
    REQUIRED: False
  - TITLE: UID
    TYPE: String
    REQUIRED: False
  - TITLE: PREFIX
    TYPE: String
    REQUIRED: False
  - TITLE: TITLE
    TYPE: String
    REQUIRED: False
- TAG: REQUIREMENT
  FIELDS:
  - TITLE: MID
    TYPE: String
    REQUIRED: False
  - TITLE: UID
    TYPE: String
    REQUIRED: False
  - TITLE: LEVEL
    TYPE: String
    REQUIRED: False
  - TITLE: STATUS
    TYPE: String
    REQUIRED: False
  - TITLE: TITLE
    TYPE: String
    REQUIRED: True
  - TITLE: STATEMENT
    TYPE: String
    REQUIRED: False
- TAG: COMPOSITE_REQUIREMENT
  PROPERTIES:
    IS_COMPOSITE: True
  FIELDS:
  - TITLE: MID
    TYPE: String
    REQUIRED: False
  - TITLE: UID
    TYPE: String
    REQUIRED: False
  - TITLE: LEVEL
    TYPE: String
    REQUIRED: False
  - TITLE: TITLE
    TYPE: String
    REQUIRED: False
  - TITLE: STATEMENT
    TYPE: String
    REQUIRED: False

[[COMPOSITE_REQUIREMENT]]
TITLE: Composite requirement one
STATEMENT: Composite requirement one

[[/COMPOSITE_REQUIREMENT]]

[[COMPOSITE_REQUIREMENT]]
LEVEL: 4.5.6
TITLE: Composite requirement two
STATEMENT: Composite requirement two

[[/COMPOSITE_REQUIREMENT]]

[[COMPOSITE_REQUIREMENT]]
TITLE: Composite requirement three
STATEMENT: Composite requirement three

[[/COMPOSITE_REQUIREMENT]]
