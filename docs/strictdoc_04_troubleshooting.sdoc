[DOCUMENT]
TITLE: Troubleshooting
UID: SDOC_TROUBLESHOOTING

[TEXT]
STATEMENT: >>>
This document summarizes solutions to the most common issues reported by StrictDoc users.
<<<

[SECTION]
TITLE: Caching issues

[TEXT]
STATEMENT: >>>
.. note::

    **TL;DR:** If you encounter errors related to reading data, make sure to delete the StrictDoc cache folder located at ``$TMPDIR/strictdoc_cache`` or in the custom directory if specified by the ``cache_dir`` option in the ``strictdoc.toml`` configuration file.

StrictDoc caches many artifacts on disk. Some artifacts are cached using Python’s `pickle <https://docs.python.org/3/library/pickle.html>`_ module, while others are written directly to disk.

The pickle module serializes Python objects to disk. The issue with this approach is that when StrictDoc changes the schema of its objects (e.g., when SDocNode or SDocDocument objects gain a new property or a property type changes), an outdated object may be read from the cache after upgrading to a new StrictDoc version. While a more systematic solution might be implemented in the future, the current workaround is to manually delete the StrictDoc cache folder.
<<<

[/SECTION]
