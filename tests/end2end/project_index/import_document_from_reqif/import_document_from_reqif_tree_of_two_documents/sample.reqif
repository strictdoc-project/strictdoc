# Documentation export by StrictDoc

# Specification: Document 1

## R1 (TEXT)
Document 1 free text.

## R2: Document 1 section (SECTION)

### R3 (TEXT)
Document 1 statement.

# Specification: Document 2

## R4 (TEXT)
Document 2 free text.

## R5: Document 2 section (SECTION)

### R6 (TEXT)
Document 2 statement.
