[DOCUMENT]
TITLE: Document 1

[REQUIREMENT]
STATEMENT: >>>
See [LINK: REQ-001].
<<<

[REQUIREMENT]
STATEMENT: >>>
See [LINK: REQ-001].
<<<

[REQUIREMENT]
UID: REQ-001
TITLE: Linked-to requirement
STATEMENT: >>>
Requirement statement.
<<<
