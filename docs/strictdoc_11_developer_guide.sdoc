[DOCUMENT]
MID: 4f05169346ab4001b6ff19e8349e8fa7
TITLE: Developer Guide
VERSION: Git commit: @GIT_VERSION, Git branch: @GIT_BRANCH
DATE: @GIT_COMMIT_DATETIME
OPTIONS:
  ENABLE_MID: True

[GRAMMAR]
ELEMENTS:
- TAG: SECTION
  PROPERTIES:
    IS_COMPOSITE: True
  FIELDS:
  - TITLE: MID
    TYPE: String
    REQUIRED: True
  - TITLE: UID
    TYPE: String
    REQUIRED: False
  - TITLE: LEVEL
    TYPE: String
    REQUIRED: False
  - TITLE: PREFIX
    TYPE: String
    REQUIRED: False
  - TITLE: TITLE
    TYPE: String
    REQUIRED: True
- TAG: TEXT
  FIELDS:
  - TITLE: MID
    TYPE: String
    REQUIRED: False
  - TITLE: STATEMENT
    TYPE: String
    REQUIRED: True
  RELATIONS:
  - TYPE: Parent
  - TYPE: File

[TEXT]
MID: f174b0cdec6b482daa2878c8cc0d02c3
STATEMENT: >>>
This section contains everything that a StrictDoc developer/contributor should
know to get the job done.

StrictDoc is based on Python and maintained as any other Python package on
GitHub: with linting, tests, and hopefully enough best practice put into the
codebase.

The instructions and conventions described below are a summary of what is
considered to be the currently preferred development style for StrictDoc.

Any feedback on this development guide is appreciated.
<<<

[[SECTION]]
MID: c069e4c7b4d04dd09eb73f940e947bfd
UID: DEVGUIDE_GETTING_STARTED
TITLE: Getting started

[[SECTION]]
MID: 7477d397d0ca493f8e47532455d44965
TITLE: System dependencies

[TEXT]
MID: df2e1de12c6b456898c48a36650813d4
STATEMENT: >>>
StrictDoc itself mostly depends on other Python Pip packages, so there is
nothing special to be installed.

You may need to install ``libtidy`` if you want to run the integration tests.
The HTML markup validation tests depend on libtidy.

On Linux Ubuntu:

.. code:: bash

    sudo apt install tidy

From the core Python packages, StrictDoc needs Invoke, uv and TOML:

.. code:: bash

    pip install invoke uv toml
<<<

[[SECTION]]
MID: b7a21564c30043acbf1733d9b47bd0bc
TITLE: Windows-specific: Long Path support

[TEXT]
MID: 8591cf6dece04244824c3ac2a8666ba3
STATEMENT: >>>
As `reported <https://github.com/strictdoc-project/strictdoc/issues/1118>`_ by a
user, Windows Long Path support has to be enabled on a Windows system.

You can find information on how to enable the long paths support at
https://pip.pypa.io/warnings/enable-long-paths.
<<<

[[/SECTION]]

[[/SECTION]]

[[SECTION]]
MID: 89ec30b9f67c489da635be391b0b0e15
TITLE: Installing StrictDoc from GitHub (developer mode)

[TEXT]
MID: 2407bb186b274a58b97b54b99ba6e86f
STATEMENT: >>>
.. note::
    Use this way of installing StrictDoc only if you want to make changes in StrictDoc's source code.
    Otherwise, install StrictDoc as a normal Pip package by running ``pip install strictdoc``.
<<<

[[SECTION]]
MID: 1814a8c25afc40cba6dca1696cae119b
TITLE: Development within a virtual environment

[TEXT]
MID: a3e14b05452b48e2a0d8726fa00a7f00
STATEMENT: >>>
This is the currently recommended approach, for those familiar with
development in a virtual environment:

.. code:: bash

    git clone https://github.com/strictdoc-project/strictdoc.git && cd strictdoc
    python3 -m venv .venv
    . ./.venv/bin/activate
    pip install -r requirements.bootstrap.txt
    uv sync --no-install-project
    python3 strictdoc/cli/main.py

.. note::

    Windows users, substitute: ``.\.venv\Scripts\activate``

This installs Invoke, uv and TOML, plus all the default dependencies of
StrictDoc. Dev-time dependencies (lint, tests, docs, ...) are installed
automatically per Invoke task, via ``uv sync --group <flavor>``; see the
"Invoke for development tasks" section below.
<<<

[[SECTION]]
MID: 66c012d712d64317bd105f0f30b304f8
TITLE: Automating the virtual environment with direnv

[TEXT]
MID: f954f57ad45e4a7c9c66ce1ffa857edc
STATEMENT: >>>
A user can install `direnv <https://direnv.net/>`_ to avoid activating the
virtual environment by hand. The repository's ``.envrc`` creates and
activates ``.venv`` automatically whenever you ``cd`` into the project
directory, once you allow it to run:

.. code:: bash

    direnv allow
<<<

[[/SECTION]]

[[/SECTION]]

[[SECTION]]
MID: c8a25b058b6441e0969370cac6577602
TITLE: Development with Nix (experimental)

[TEXT]
MID: 26106facb63c4f1581475f297ae763c1
STATEMENT: >>>
.. note::
    This workflow is experimental.

For those who have `Nix <https://nixos.org/download/>`_ installed, StrictDoc
provides a ``flake.nix``-based dev shell as an alternative to the
``.envrc`` + ``.venv`` + Invoke workflow described above. The two do not
share a virtual environment.

The Nix dev shell provides a Python interpreter with the runtime
dependencies of ``pyproject.toml`` and with Invoke and uv already installed,
plus the tools that are not Python packages: ``libtidy`` (integration
tests), Chromium and a matching driver (end2end and screencast tests), and
``github_changelog_generator``.

To enter an interactive dev shell:

.. code:: bash

    ./bootstrap_nix.sh

To run a single command inside the dev shell without entering it
interactively:

.. code:: bash

    ./bootstrap_nix.sh <cmd>

Once inside the shell, use Invoke as usual, for example ``invoke check``.
Invoke still runs every task through uv, which creates its own virtual
environments under ``build/uv/<flavor>``; with Nix, the runtime dependencies
of ``pyproject.toml`` come from the Nix shell, so uv only needs to install
each flavor's extra dependency group.
<<<

[[/SECTION]]

[[/SECTION]]

[[/SECTION]]

[[SECTION]]
MID: 90d5d79146e64660a71cd74ac23f6811
TITLE: Invoke for development tasks

[TEXT]
MID: 452b3c24463446a497ed6b8fcdb31fef
STATEMENT: >>>
All development tasks are managed using `Invoke <https://www.pyinvoke.org/>`_ in
the ``tasks.py`` file. On macOS and Linux, all tasks run in dedicated virtual
environments. On Windows, invoke uses the parent pip environment, which can be a
system environment or a user's virtual environment.

Make sure to familiarize yourself with the available developer tasks by running:

.. code-block:: bash

    invoke --list
<<<

[[/SECTION]]

[[SECTION]]
MID: e7ce6a2f13614974b43aba56f6ae7253
TITLE: Main "Check" task

[TEXT]
MID: 09258e99cabb4455904b0e2c6687d492
STATEMENT: >>>
Before doing anything else, run the main ``check`` command to make sure that
StrictDoc passes all tests on your system:

.. code:: bash

    invoke check

The ``check`` command runs all StrictDoc lint and test tasks with the only
exception of end-to-end Web tests that are run with a separate task (see below).
<<<

[[/SECTION]]

[[SECTION]]
MID: 5d4a3e19e1c545e98cf759eaac5b9281
TITLE: Linting

[[SECTION]]
MID: b164c82aab8148b587b24eed5684eedc
TITLE: Black for Python code formatting

[TEXT]
MID: 0a8c138cb2f2415184007ab20080e9ca
STATEMENT: >>>
Formatting is governed by ``black`` which reformats the code automatically when
the ``invoke lint`` command is run.
<<<

[[/SECTION]]

[[/SECTION]]

[[SECTION]]
MID: 07d9a3c17be8475089844f5eb2cd8299
UID: DEVGUIDE_PYTHON_CODE
TITLE: Python code

[[SECTION]]
MID: 79d5eb35cec141939bdce042a98acef7
TITLE: Python version

[TEXT]
MID: 1d9ec1c5b17240ec8fed8ea34646bd32
STATEMENT: >>>
Set the Python version as low as possible given some constraints of StrictDoc's
dependencies.

Raise the Python version baseline only when it is consistently deprecated by
major software platforms like Ubuntu or GitHub Actions.
<<<

[[/SECTION]]

[[SECTION]]
MID: 9aed2e7119104783a5cf1813f6ded390
TITLE: Line length

[TEXT]
MID: 32813f4a974d4f3cb9b5f810c1a60a05
STATEMENT: >>>
For Python code, use line length of 80.

If a string literal gets too long, it should be converted into a multiline
literal with each line being a meaningful word or a subsentence.
<<<

[[/SECTION]]

[[SECTION]]
MID: 534c96bdbf6d4835a21c15cf5f8726ea
TITLE: Strong type system

[TEXT]
MID: 647dd970e02540309165d6fdf2da1b5d
STATEMENT: >>>
Use explicit types everywhere.

**NOTE**: StrictDoc has been making a gradual shift towards a stronger type
system. Although type annotations haven't been added everywhere in the codebase,
it is preferred to include them for all new code that is written.
<<<

[[/SECTION]]

[[SECTION]]
MID: f724206a1eb5471ab7959cc9c9c1e26f
TITLE: Order and naming of functions

[TEXT]
MID: dbbd427ead5743bc9ab737ed006578ae
STATEMENT: >>>
The order of functions in a Python module or class shall follow the "newspaper
style":

- Place public functions above all private functions.
- The private functions shall start with the ``_`` character.
<<<

[[/SECTION]]

[[SECTION]]
MID: 5ac20ad28f0e416689d6310ab7828c56
TITLE: Full descriptive names

[TEXT]
MID: 32dc22fe23604c87b01dfdafbd80b730
STATEMENT: >>>
Avoid shortening variable names unnecessarily. For example, use 'buffer' instead
of 'buf', 'document' instead of 'doc', 'function' instead of 'func', 'length'
instead of 'len', etc.

NOTE: While some older parts of StrictDoc may not adhere to this guideline, they
are planned to be refactored in the future.
<<<

[[/SECTION]]

[[SECTION]]
MID: 0c5d9420267546798561c3a8ec648145
TITLE: Short-lived/temporary variables

[TEXT]
MID: 3bc4e3b017374963a75f59458ed43a21
STATEMENT: >>>
For lambdas and short for loops, append a trailing underscore (``_``) to
variable names to visually indicate that they are temporary and intended for use
only within the local scope of the lambda or loop.

This convention helps with local reasoning and mitigates the fact that Python
loop variables are not block-scoped and remain accessible after the loop has
finished.

Example:

.. code-block:: python

    for foo_, bar_ in baz:
        # Use foo_ and bar_ only within the loop.
<<<

[[/SECTION]]

[[SECTION]]
MID: 2c6b471674304324a5bb51fcaf5387a1
TITLE: Explicit If-checks

[TEXT]
MID: bdb6039d3ab8439c9474c5b266e6fa0f
STATEMENT: >>>
For "element is non-None" checks, always use the full form.

Example: ``if foo is not None`` instead of ``if foo``.

The non-None and non-empty string check shall be as follows: ``if foo is not
None and len(foo) > 0``. The explicit check also applies to any other kinds of
objects besides strings: ``if foo is not None`` instead of ``if foo``.

**Rationale**:

The use of ``if foo`` makes it unclear whether the intention is to check ``is
not None`` or also ``len(foo) > 0``.

This helps to avoid any confusion with all sorts of strings (empty or non-empty
``str``, ``Optional[str]``) that are used extensively in StrictDoc's codebase.
<<<

[[/SECTION]]

[[SECTION]]
MID: 223daa23c5d645eaa5abe0a5a8b1c633
TITLE: Opening files

[TEXT]
MID: 4e05d9b1a86b4b8bb0c4b6adb9933e86
STATEMENT: >>>
For opening files, use the helpers ``file_open_read_utf8`` and
``file_open_read_bytes``.

These helpers perform normal file opening but also strip the UTF-8 BOM
character, which is added by some Windows tools.
<<<

[[/SECTION]]

[[/SECTION]]

[[SECTION]]
MID: 6e9707c99199464583f091056d1ae458
UID: DEVGUIDE_GIT_WORKFLOW
TITLE: Git workflow

[[SECTION]]
MID: 697ff4fa8bf14dbb88bf9021a50729ed
TITLE: Commit and pull request workflow

[TEXT]
MID: 32a1967e18f942d697e67adf52466870
STATEMENT: >>>
For smaller pull requests, the preferred Git workflow is "1 commit per 1 PR".

If the work truly deserves a sequence of commits, each commit shall be
self-contained and pass all checks from the ``invoke check`` command.

For larger pull requests involving too many changes, the preferred approach:
split the work into several independent PRs to simplify the work of the
reviewer.

When resolving conflicts, the development branch should be always rebased
against the main branch. Merging ``main`` into development branches shall be
avoided, i.e.,

**Preferred**: ``git fetch && git rebase origin/main``

**Avoid**: ``git fetch && git merge main``

Contributors are encouraged to proactively use ``git rebase --interactive`` to
refine their commit history into self-contained commits before opening a GitHub
pull request.
<<<

[[/SECTION]]

[[SECTION]]
MID: 39e26da767964709ada28fde7a2d417b
UID: DEVGUIDE_GIT_COMMIT_MESSAGE
TITLE: Git commit message

[TEXT]
MID: abd7a4dc753142928e9a2d31251fb2e9
STATEMENT: >>>
The Git commit message should follow the format of
`Conventional Commits <https://www.conventionalcommits.org/en/v1.0.0/>`_:

.. code-block::

    <type>(<optional scope>): <description>

where the ``scope`` can be a major feature being added or a folder.

A form of ``<type>(scope): <subscope>: <description>`` is also an option.

Examples:

.. code-block::

    feat(html2pdf): add a new option to force page breaks
    fix(backend/sdoc_source_code): add Rust support
    refactor(cli): migrate "import excel" to command pattern
    chore(cli): rename shared.py -> _shared.py
    chore(.github): switch the macOS tests to macos-latest
    docs: update release notes

If the committed work is dedicated to more than one topic, use comma-separated
scopes. Example:

.. code-block::

    refactor(server, UI): update to new requirement styles

.. note::

    The Conventional Commits specification lists ``scope`` as optional. However, most StrictDoc commits do have a scope. Most of the time, there is a specific feature or area being worked on, so it should be straightforward to identify the right scope.
<<<

[[/SECTION]]

[[/SECTION]]

[[SECTION]]
MID: 2420b2d7a4624bd99b0f8088dfa9abff
TITLE: Frontend development

[TEXT]
MID: d818aad87db54985b8933f98528808ab
STATEMENT: >>>
The shortest path to run the server when the StrictDoc's source code is cloned:

.. code-block:: bash

    invoke server
<<<

[[/SECTION]]

[[SECTION]]
MID: 99a11c81fdbd422ca597eabd1e9dc538
TITLE: Testing

[TEXT]
MID: e48e78597c404e4288cae4e39e854ecb
STATEMENT: >>>
For every new feature, write at least one new integration or end-to-end test.

For modifications to existing code, add new or adapt the existing test to
exercise the new behavior.

If the contributed code needs a fine-grained control over the added behavior,
adding both unit and integration tests is preferred. The only exception where a
contribution can contain no tests is ``refactoring`` or ``chore`` (code climate)
work which is work that introduces changes in code but no change to the
functionality.
<<<

[[SECTION]]
MID: 240dc1426d994397ac1401834b4f0ef0
TITLE: Running integration tests

[TEXT]
MID: 4e307b3b950840bbbe455c1ae3238a6e
STATEMENT: >>>
The integration tests are run using Invoke:

.. code-block:: bash

    invoke test-integration

The ``--focus`` parameter can be used to run only selected tests that match a
given substring. This helps to avoid running all tests all the time.

.. code-block:: bash

    invoke test-integration --focus <keyword>

See
`How to test command-line programs with Python tools: LIT and FileCheck <https://stanislaw.github.io/2020-11-20-how-to-test-command-line-programs-with-python.html>`_
to learn more about LIT and FileCheck, which enable the StrictDoc integration
tests.
<<<

[[/SECTION]]

[[SECTION]]
MID: 73c717608cce4abca2c768f1dbfb705d
TITLE: Running End-to-End Web tests

[TEXT]
MID: da3cbcd69b0545988daeb0f42098830d
STATEMENT: >>>
.. code:: bash

    invoke test-end2end
<<<

[[/SECTION]]

[[/SECTION]]

[[SECTION]]
MID: 7b4bf839b1c44b0d82001060596d8cbf
TITLE: Documentation

[TEXT]
MID: d1f5fde86ebc4103bc4eb0334b1ec919
STATEMENT: >>>
- Every change in the functionality or the infrastructure should be documented.
- Every line of documentation shall be no longer than 80 characters. StrictDoc's
  own documentation has a few exceptions, however, the latest preference is
  given to 80 characters per line. Unfortunately, until there is automatic
  support for mixed SDoc/RST content, all long lines shall be edited and
  split by a contributor manually.
- The ``invoke docs`` task should be used for re-generating documentation on a
  developer machine.
<<<

[[/SECTION]]

[[SECTION]]
MID: d20e67d776c04dfab340c924bb70e89f
TITLE: Technical writing

[TEXT]
MID: 33b4625be18043f7968fff19781633ac
STATEMENT: >>>
These guidelines for technical writing apply to humans and AI.

They are applicable to:

- Documentation
- Code comments
- PR descriptions.
<<<

[[SECTION]]
MID: f14fc2e61fe043ab965fcffb8ae49dfb
TITLE: Basic rules

[TEXT]
MID: 4902476cf7ef47568e3e38c4341cd9cf
STATEMENT: >>>
**1. Use sentence case.**

Use ``Sentence case``, not ``Title Case``, for headings, titles, and similar
text. Capitalize only the first word and any proper nouns.

Example: write ``Managing dependencies with Python``, not ``Managing
Dependencies With Python``.
<<<

[[/SECTION]]

[[SECTION]]
MID: 116a9118528547218531062e01822b9d
TITLE: Concise technical writing

[TEXT]
MID: a2835e1fc0894db1b6369d937880cd2a
STATEMENT: >>>
Keep all technical writing terse and tight.

**1. Keep sentences short.**

Aim for 15–20 words per sentence and treat 25 words as a soft limit. If a
sentence exceeds 25 words, check whether it can be split without losing clarity
or technical precision.

**2. Use the minimum wording required for precision and clarity.**

Weak: "In order to be able to perform the validation, the system needs to first
load the configuration file."

Better: "To validate, the system first loads the configuration file."

**3. Prefer direct statements over indirect or elaborate phrasing.**

Weak: "It should be noted that the parser is not currently capable of handling
empty sections."

Better: "The parser does not support empty sections."

**4. Remove filler, repetition, redundant qualifiers, and unnecessary
transitions.**

Weak: "Basically, this means that the function will simply return the same value
again."

Better: "The function returns the same value."

**5. Keep sentences and paragraphs focused on one point.**

Weak: "The command writes the output to disk, and it also validates the
configuration, which is useful because invalid configuration can otherwise cause
failures later."

Better: "The command validates the configuration before writing the output to
disk. This prevents later failures caused by invalid configuration."

**6. Do not repeat information unless repetition is necessary for
understanding.**

Weak: "The cache is cleared on startup. This means that every startup clears the
cache."

Better: "The cache is cleared on startup."

**7. Preserve technical accuracy and essential context; brevity must not make
the text ambiguous.**

Too terse: "The request fails after 5 seconds."

Better: "The request times out if no response is received within 5 seconds."
<<<

[[/SECTION]]

[[SECTION]]
MID: 5f060e0df0ab4eb8b2d09996289822e2
TITLE: More structure, less prose

[TEXT]
MID: acd948cee2f94612a30d5d79313acaab
STATEMENT: >>>
Keep sections and paragraphs focused and short. Each section should cover one
coherent topic, and each paragraph should explain one main idea.

Split long paragraphs into smaller paragraphs or sentences when they contain
multiple ideas. If a section becomes too broad, split it into focused
subsections.

When presenting an enumeration, use bullet points or a numbered list instead of
embedding multiple items in a long sentence.

This structure reduces context switching and makes technical documents easier to
scan, understand, navigate, and maintain.
<<<

[[/SECTION]]

[[SECTION]]
MID: e985ff5ffc244e42b2d64ab7c5830717
TITLE: Use Bottom Line Up Front style

[TEXT]
MID: b8da36976717443fa52a52b691b1ec48
STATEMENT: >>>
Present the main point first, then provide supporting details. Readers should
understand the conclusion, decision, or request without reading the entire
message.

This is a **deductive** writing style: start with the conclusion, then explain
the reasoning, evidence, or background that supports it. Avoid an **inductive**
structure, where the reader must follow the entire chain of reasoning before
discovering the main point at the end. Deductive writing reduces cognitive
effort and helps readers decide immediately whether they need to read the
supporting details.
<<<

[[/SECTION]]

[[SECTION]]
MID: 9f3e125d01934a0fac7de7396d1e836a
TITLE: Use active voice

[TEXT]
MID: 0f8b436e783e4cc986139172a61e89f8
STATEMENT: >>>
State who did what instead of using passive constructions. This makes messages
easier to understand and reduces ambiguity about ownership and actions. Active
voice makes responsibilities, decisions, and actions explicit, allowing readers
to quickly identify who is responsible for each action. Use passive voice only
when the actor is genuinely unknown or irrelevant.

**Recommended**: The engineer linked the requirement to the test case.

**Not recommended**: The requirement was linked to the test case.
<<<

[[/SECTION]]

[[/SECTION]]

[[SECTION]]
MID: a44e3b99323b4ac291f4b4d3948c3cc0
TITLE: Conventions

[TEXT]
MID: 49b7349a3bee478cbe81d8ef25f6245c
STATEMENT: >>>
- ``snake_case`` everywhere, no ``kebab-case``.

  - This rule applies everywhere where applicable: file and folder names, HTML attributes.
  - Exception: HTML data-attributes and ``testid`` identifiers.
<<<

[[/SECTION]]

[[SECTION]]
MID: 57300bfdfcaf47c2ab7b29c3e6ffb75d
TITLE: Playbooks

[[SECTION]]
MID: fc6903ec4e7d4150bd080acb5ace7032
TITLE: Software development

[TEXT]
MID: ee60e2514d664e3db2dc7a1a79e0e84f
STATEMENT: >>>
- Use this Dev Guide to perform any software development.
- Use ``invoke lint`` for linting.
- Use ``invoke test-*`` tasks with ``--focus`` argument when iterating on new or
  existing features.
- For features and bugfixes, generate release notes.
<<<

[[/SECTION]]

[[SECTION]]
MID: 6463378e6d714365a7801fa6fd23a2b5
TITLE: Requirements management

[TEXT]
MID: 2afa551d70d04e3c88946319a7097ea8
STATEMENT: >>>
The StrictDoc requirements are split into three levels: L1, L2, and L3. These
levels correspond to WHY-WHAT-HOW.

Level 1 (WHY):

* Captures requirements towards "a requirements tool".
* These requirements can be seen as stakeholder requirements in the sense of
  general systems engineering.
* Does not contain any StrictDoc-specific requirements.
* Does not contain any StrictDoc-specific artifacts, such as references to code,
  classes, folder structure, Git repositories, etc.
* The L1 document structure is organized according to broad feature clusters
  expected from a requirements tool.
* The L1 content assumes that multiple tools could be implemented based on L1.
  It shall not be hard-coded to StrictDoc.

Level 2 (WHAT):

* Captures high-level requirements (HLR) towards StrictDoc as a concrete
  requirements tool.
* The requirements at this level describe WHAT before design, meaning that they
  do not touch implementation details.
* The L2 requirements shall not dictate the underlying design or implementation
  too much. Specific implementation details are delegated to L3.
* The L2 document's table of contents is organized according to StrictDoc
  Features at the top level and Capabilities at the next levels of nesting.

Level 3 (HOW):

* Captures low-level requirements (LLR) towards specific StrictDoc software
  components and implementation details.
* The low-level requirements describe the HOW of StrictDoc.
* The low-level requirements are written during or after design.
* The low-level requirements are the lowest and final requirements level before
  the actual implementation.
* The low-level requirements are still testable "shall" statements.
* The L3 requirements document's table of contents is organized according to
  StrictDoc Features. Each Feature is further structured according to the
  contributing software components, with section titles corresponding to folders
  and files.
<<<

[[SECTION]]
MID: 074db0f544644d818fb78601cfaef691
TITLE: Features and Capabilities

[TEXT]
MID: 3d46d9d74b3b434aa141bbd669a1d2eb
STATEMENT: >>>
StrictDoc's development uses two concepts, "Feature" and "Capability", to better
structure requirements and other documentation.

A Feature is a major slice of StrictDoc's functionality. Features are controlled
in StrictDoc's configuration via the `project_features` property.

A Capability can be seen as a smaller Feature. One Feature can contain multiple
Capabilities. A Capability can also span multiple Features.

Examples of Features: Document screen, HTML2PDF, Project statistics.

Examples of Capabilities: automatic generation of requirement identifiers,
customized HTML2PDF template, parsing @relation markers as part of the
requirement-to-source traceability feature.

.. note:: When structuring L2 documents, if a Feature contains multiple functionally related requirements, this could indicate that these requirements should be maintained as part of a Capability.
<<<

[[/SECTION]]

[[SECTION]]
MID: 95c05391367c41f2a9ec2f064b6e67d6
TITLE: Requirements traceability

[TEXT]
MID: 247d65cb14914dde8fe5e2c670898dfa
STATEMENT: >>>
The ideal state of the L1-L2-L3 requirements flowdown is full bidirectional
traceability between all levels.

The requirements are as follows:

* Each L1 requirement must have at least one L2 requirement that references it
  as a parent.
* Each L2 requirement must have at least one L3 requirement that references it
  as a parent.
* The levels must not be skipped. L3 must not reference L1 directly, and L1 must
  not reference L3.
* Source code and tests can reference both L2 and L3 requirements via @relation
  markers.
* As a general soft guideline, L2 requirements are referenced by higher-level
  implementation code and tests, while L3 requirements are referenced by
  specific implementation snippets or lower levels of testing, such as unit
  tests.
<<<

[[/SECTION]]

[[SECTION]]
MID: 9af25b626ee74fbb8add9d015c332349
TITLE: EARS syntax

[TEXT]
MID: aad06acc21844f8f87ae3b8f114c96ef
STATEMENT: >>>
EARS (Easy Approach to Requirements Syntax) is a small set of sentence
templates for writing "shall" requirement statements unambiguously. Each
template combines a trigger/condition clause with a system response clause,
for example:

* Ubiquitous: ``The <system> shall <response>.``
* Event-driven: ``When <trigger>, the <system> shall <response>.``
* State-driven: ``While <state>, the <system> shall <response>.``
* Unwanted behavior: ``If <trigger>, then the <system> shall <response>.``
* Optional feature: ``Where <feature>, the <system> shall <response>.``

EARS shall be used for writing requirement statements at all levels (L1, L2,
L3). It keeps requirements testable and reduces ambiguity for both human
developers and AI.

See `the original EARS page <https://alistairmavin.com/ears/>`_ for more
details.

.. note:: EARS is the default, but exceptions are allowed. In some cases, StrictDoc's requirements writing allows "hybrid" requirements with more than one shall statement per requirement, or shall statements complemented by additional content that explains or expands on the requirement's applicability or scope.
<<<

[[/SECTION]]

[[SECTION]]
MID: 9e15aae3c55f4cd483d2c0a75a365fff
TITLE: Ongoing requirements work

[TEXT]
MID: 633ab2a2f430453b8d337b67de75ea5d
STATEMENT: >>>
The StrictDoc requirements documentation is an evolving process. The following
aspects are continuously reworked and still need improvement:

* The requirements writing shall follow the technical writing guidelines and the EARS syntax described in this developer guide.
* StrictDoc's development relies on AI-assisted work. Due to the limited
  development resources of the core team, the development process relies more
  strongly on L2 than on L3. The first priority is to maintain a strong L2/HLR
  baseline, while L3/LLR can have gaps in documenting the implementation.
  Nevertheless, the L3 level is gradually being built up with HOW requirements
  that govern important implementation details that must be respected by both
  human developers and AI.
* Do not be surprised if some legacy L2 requirements match the L3 definition.
  These requirements shall be gradually relocated from L2 to L3.
* The traceability links shall be established between all requirements. If a
  link is missing, it has to be fixed eventually.
* The conceptual split between Feature and Capability is relatively new and has
  not yet been applied consistently across the L2 and L3 documents. New
  requirements development will use this concept for both newly developed
  requirements and the gradual migration of existing requirements.
<<<

[[/SECTION]]

[[/SECTION]]

[[SECTION]]
MID: e30a730c91d94de28b62f471f0a67e04
TITLE: How to update release notes

[TEXT]
MID: e06a9159c4be4555acd67d77f445c968
STATEMENT: >>>
- Add to the release notes (``docs/strictdoc_04_release_notes.sdoc``) a
  high-level, human-readable summary of all work since the latest Git tag.
- Summarize all changes under the top section called "Unreleased". If that
  section does not exist yet, create it. It is this section that will later be
  turned into the actual release notes.
- The section shall start with ``This release contains the following
  enhancements:<full empty line break>``.
- Follow the example of the existing Release Notes.
- Do not summarize each and every commit. Only include the most important
  user-facing changes that are implemented with ``feat:`` and ``fix:`` commits.
  Don't consider commits with any other prefix.
- Ignore the changelog file ``CHANGELOG.md`` completely. It is an outdated
  auto-generated file that is going to be removed in the future.
- Do not try to create a new version yourself. This is handled with another
  playbook (TBD).
- Do not modify any existing content from the previous releases.
<<<

[[/SECTION]]

[[/SECTION]]
