[DOCUMENT]
TITLE: Dummy Software Requirements Specification #3

[TEXT]
STATEMENT: >>>
.. image:: _assets/file.svg
   :alt: Test image
   :class: image
   :width: 100%
<<<

[TEXT]
STATEMENT: >>>
[LINK: SEC-1]
<<<
