[DOCUMENT]
TITLE: Document 1

[GRAMMAR]
ELEMENTS:
- TAG: TEXT
  FIELDS:
  - TITLE: UID
    TYPE: String
    REQUIRED: False
  - TITLE: STATEMENT
    TYPE: String
    REQUIRED: True
- TAG: REQUIREMENT
  FIELDS:
  - TITLE: UID
    TYPE: String
    REQUIRED: False
  - TITLE: TITLE
    TYPE: String
    REQUIRED: False
  - TITLE: STATEMENT
    TYPE: String
    REQUIRED: False
  RELATIONS:
  - TYPE: Child
    ROLE: Refines
  - TYPE: Child
    ROLE: Implements

[REQUIREMENT]
UID: REQ-001
TITLE: Requirement title #1
STATEMENT: >>>
Requirement statement #1.
<<<

[REQUIREMENT]
UID: REQ-002
TITLE: Requirement title #2
STATEMENT: >>>
Requirement statement #2.
<<<

[REQUIREMENT]
UID: REQ-003
TITLE: Requirement title #3
STATEMENT: >>>
Requirement statement #3.
<<<
RELATIONS:
- TYPE: Child
  VALUE: REQ-001
  ROLE: Refines
- TYPE: Child
  VALUE: REQ-002
  ROLE: Implements
