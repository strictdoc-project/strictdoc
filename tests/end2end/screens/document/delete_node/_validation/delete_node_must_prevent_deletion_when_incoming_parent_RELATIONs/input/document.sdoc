[DOCUMENT]
TITLE: Document 1

[REQUIREMENT]
UID: REQ-1
TITLE: Requirement title #1
STATEMENT: >>>
Requirement statement #1.
<<<

[REQUIREMENT]
UID: REQ-2
TITLE: Requirement title #2
STATEMENT: >>>
Requirement statement #2.
<<<
RELATIONS:
- TYPE: Parent
  VALUE: REQ-1

[REQUIREMENT]
UID: REQ-3
TITLE: Requirement title #3
STATEMENT: >>>
Requirement statement #3.
<<<
RELATIONS:
- TYPE: Parent
  VALUE: REQ-1
