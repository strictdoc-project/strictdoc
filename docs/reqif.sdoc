[DOCUMENT]
TITLE: StrictDoc/ReqIF

[SECTION]
TITLE: Introduction

[FREETEXT]
TODO
[/FREETEXT]

[/SECTION]

[SECTION]
TITLE: Relevant resources

[FREETEXT]
- OMG standard: `Requirements Interchange Format (ReqIF), Version 1.2 <https://www.omg.org/spec/ReqIF/1.2/PDF>`_
- `How the ReqIF Standard for Requirements Exchange Disrupts the Tool Market <https://re-magazine.ireb.org/articles/open-up#fn-13>`_
- `ReqIF Implementation Guide <https://www.prostep.org/fileadmin/downloads/PSI_ImplementationGuide_ReqIF_V1-7.pdf>`_
[/FREETEXT]

[/SECTION]

[SECTION]
TITLE: ReqIF Overview

[FREETEXT]

**Spec Object**: Represents an atomic requirement item.

**Spec Relation**: encodes a relationship between two Spec Objects.
[/FREETEXT]

[/SECTION]

[SECTION]
TITLE: Implementation outline (TODO)

[FREETEXT]
- Section: What is common in all ReqIF documents?

- Section: What is special in every ReqIF document?
[/FREETEXT]

[/SECTION]

[SECTION]
TITLE: Two-stage parsing

[FREETEXT]
[/FREETEXT]

[/SECTION]

[SECTION]
TITLE: First stage: parsing ReqIF into Objects

[FREETEXT]
When stable, the first stage is a candidate for an extraction to a
separate ReqIF parser (Pip package).
[/FREETEXT]

[/SECTION]

[SECTION]
TITLE: Stage stage: Building SDoc from a ReqIF bundle

[FREETEXT]
Building an SDoc document from the "ReqIF document bundle"
based on a provided mapping.
[/FREETEXT]

[SECTION]
TITLE: Native StrictDoc

[FREETEXT]
TBD
[/FREETEXT]

[/SECTION]

[SECTION]
TITLE: Doors-like ReqIF schema parser

[FREETEXT]
TBD
[/FREETEXT]

[/SECTION]

[/SECTION]
