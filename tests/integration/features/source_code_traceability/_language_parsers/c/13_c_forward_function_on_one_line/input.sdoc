[DOCUMENT]
TITLE: Document 1

[REQUIREMENT]
UID: REQ-1
TITLE: Requirement title
STATEMENT: Requirement statement.
RELATIONS:
- TYPE: File
  VALUE: file.c
  FUNCTION: fn1
- TYPE: File
  VALUE: file.c
  FUNCTION: fn2
