[DOCUMENT]
TITLE: Doc 1

[REQUIREMENT]
UID: REQ-001
STATEMENT: Hello world 1
RELATIONS:
- TYPE: Parent
  VALUE: REQ-002

[REQUIREMENT]
UID: REQ-002
STATEMENT: Hello world 2
RELATIONS:
- TYPE: Parent
  VALUE: REQ-001
