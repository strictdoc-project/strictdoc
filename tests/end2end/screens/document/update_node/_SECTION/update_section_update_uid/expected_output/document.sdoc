[DOCUMENT]
TITLE: Document 1

[TEXT]
STATEMENT: >>>
Hello world!
<<<

[[SECTION]]
UID: Section-UID-After
TITLE: First section

[TEXT]
STATEMENT: >>>
This is a free text of this section.
<<<

[[/SECTION]]
