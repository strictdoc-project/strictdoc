[DOCUMENT]
MID: 6a8bc1d467c348dbad29707cd6a3f260
TITLE: Static HTML search Test
OPTIONS:
  ENABLE_MID: True

[REQUIREMENT]
MID: req_without_uid
TITLE: Requirement without UID
STATEMENT: >>>
This requirement has no UID.
<<<

[REQUIREMENT]
MID: req1
UID: REQ-1
TITLE: Requirement #1
STATEMENT: >>>
UNIQUE_STATEMENT_LINE_1

COMMON STATEMENT LINE 1
<<<
RATIONALE: >>>
UNIQUE_RATIONALE_LINE_1

COMMON RATIONALE LINE 1
<<<

[REQUIREMENT]
MID: req2
UID: REQ-2
TITLE: Requirement #2
STATEMENT: >>>
UNIQUE_STATEMENT_LINE_2

COMMON STATEMENT LINE 2
<<<
RATIONALE: >>>
UNIQUE_RATIONALE_LINE_2

COMMON RATIONALE LINE 2
<<<

[REQUIREMENT]
MID: req3
UID: REQ-3
TITLE: Requirement #3
STATEMENT: >>>
UNIQUE_STATEMENT_LINE_3

COMMON STATEMENT LINE 3
<<<
RATIONALE: >>>
UNIQUE_RATIONALE_LINE_3

COMMON RATIONALE LINE 3
<<<

[REQUIREMENT]
MID: req4
UID: REQ-4
TITLE: Requirement #4
STATEMENT: >>>
UNIQUE_STATEMENT_LINE_4

COMMON STATEMENT LINE 4
<<<
RATIONALE: >>>
UNIQUE_RATIONALE_LINE_4

COMMON RATIONALE LINE 4
<<<

[REQUIREMENT]
MID: req5
UID: REQ-5
TITLE: Requirement #5
STATEMENT: >>>
UNIQUE_STATEMENT_LINE_5

COMMON STATEMENT LINE 5
<<<
RATIONALE: >>>
UNIQUE_RATIONALE_LINE_5

COMMON RATIONALE LINE 5
<<<

[REQUIREMENT]
MID: req6
UID: REQ-6
TITLE: Requirement #6
STATEMENT: >>>
UNIQUE_STATEMENT_LINE_6

COMMON STATEMENT LINE 6
<<<
RATIONALE: >>>
UNIQUE_RATIONALE_LINE_6

COMMON RATIONALE LINE 6
<<<

[REQUIREMENT]
MID: req7
UID: REQ-7
TITLE: Requirement #7
STATEMENT: >>>
UNIQUE_STATEMENT_LINE_7

COMMON STATEMENT LINE 7
<<<
RATIONALE: >>>
UNIQUE_RATIONALE_LINE_7

COMMON RATIONALE LINE 7
<<<

[REQUIREMENT]
MID: req8
UID: REQ-8
TITLE: Requirement #8
STATEMENT: >>>
UNIQUE_STATEMENT_LINE_8

COMMON STATEMENT LINE 8
<<<
RATIONALE: >>>
UNIQUE_RATIONALE_LINE_8

COMMON RATIONALE LINE 8
<<<

[REQUIREMENT]
MID: req9
UID: REQ-9
TITLE: Requirement #9
STATEMENT: >>>
UNIQUE_STATEMENT_LINE_9

COMMON STATEMENT LINE 9
<<<
RATIONALE: >>>
UNIQUE_RATIONALE_LINE_9

COMMON RATIONALE LINE 9
<<<

[REQUIREMENT]
MID: req10
UID: REQ-10
TITLE: Requirement #10
STATEMENT: >>>
UNIQUE_STATEMENT_LINE_10

COMMON STATEMENT LINE 10
<<<
RATIONALE: >>>
UNIQUE_RATIONALE_LINE_10

COMMON RATIONALE LINE 10
<<<

[REQUIREMENT]
MID: req11
UID: REQ-11
TITLE: Requirement #11
STATEMENT: >>>
UNIQUE_STATEMENT_LINE_11

COMMON STATEMENT LINE 11
<<<
RATIONALE: >>>
UNIQUE_RATIONALE_LINE_11

COMMON RATIONALE LINE 11
<<<

[REQUIREMENT]
MID: req12
UID: REQ-12
TITLE: Requirement #12
STATEMENT: >>>
UNIQUE_STATEMENT_LINE_12

COMMON STATEMENT LINE 12
<<<
RATIONALE: >>>
UNIQUE_RATIONALE_LINE_12

COMMON RATIONALE LINE 12
<<<

[REQUIREMENT]
MID: req13
UID: REQ-13
TITLE: Requirement #13
STATEMENT: >>>
UNIQUE_STATEMENT_LINE_13

COMMON STATEMENT LINE 13
<<<
RATIONALE: >>>
UNIQUE_RATIONALE_LINE_13

COMMON RATIONALE LINE 13
<<<

[REQUIREMENT]
MID: req14
UID: REQ-14
TITLE: Requirement #14
STATEMENT: >>>
UNIQUE_STATEMENT_LINE_14

COMMON STATEMENT LINE 14
<<<
RATIONALE: >>>
UNIQUE_RATIONALE_LINE_14

COMMON RATIONALE LINE 14
<<<

[REQUIREMENT]
MID: req15
UID: REQ-15
TITLE: Requirement #15
STATEMENT: >>>
UNIQUE_STATEMENT_LINE_15

COMMON STATEMENT LINE 15
<<<
RATIONALE: >>>
UNIQUE_RATIONALE_LINE_15

COMMON RATIONALE LINE 15
<<<
