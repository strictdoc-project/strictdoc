[DOCUMENT]
TITLE: StrictDoc Development Plan
OPTIONS:
  REQUIREMENT_STYLE: Table

[FREETEXT]
This document presents the goals of the StrictDoc project and describes how the
project is developed.
[/FREETEXT]

[SECTION]
TITLE: Project goals

[FREETEXT]
StrictDoc is an attempt to create an open source tool for writing
technical requirements specifications.
[/FREETEXT]

[REQUIREMENT]
UID: GOAL-1-TOOL-SUPPORT
TITLE: Software support for writing requirements and specifications documents
STATEMENT: >>>
There shall exist free and lightweight yet capable software for writing
requirements and specifications documents
<<<
COMMENT: >>>
Technical documentation is hard, it can be an extremely laborious process.
Software shall support engineers in their work with documentation.
<<<
COMMENT: >>>
The state of the art for many small companies working with
requirements: using Excel for requirements management in the projects with
hundreds or thousands of requirements.
<<<

[REQUIREMENT]
UID: GOAL-2-REDUCE-DOCUMENTATION-HAZARDS
TITLE: Reduce documentation hazards
STATEMENT: >>>
There shall exist no (or less) opportunity for writing incorrect or inconsistent
documentation.
<<<
COMMENT: >>>
Every serious engineering activity, such as safety engineering or systems
engineering, starts with requirements. The more critical is a product the higher
the importance of good documentation.

Technical documentation can be and often becomes a source of hazards.
It is recognized that many failures stem from inadequate requirements
engineering. While it is not possible to fix the problem of inadequate
requirements engineering in general, it is definitely possible to improve
software that supports engineers in activities such as requirements engineering
and writing technical documentation.
<<<

[REQUIREMENT]
UID: GOAL-3-NO-RUNAWAY-DOCUMENTATION
TITLE: No (or less) run-away documentation
STATEMENT: Software shall support engineers in keeping documentation up-to-date.
COMMENT: >>>
Technical documentation easily becomes outdated. Many existing tools for
documentation do not provide any measures for ensuring overall consistency of
documents and documentation trees.
<<<

[REQUIREMENT]
UID: GOAL-4-CHANGE-MANAGEMENT
TITLE: Change management
STATEMENT: Software shall provide capabilities for change management and impact assessment.
COMMENT: >>>
Change management is difficult. The bigger the project is, the harder it is to
maintain its documentation. If a change is introduced to a project, it usually
requires a full revision of its requirements.
<<<
COMMENT: >>>
When the basic capabilities of StrictDoc are in place, it should be possible
to do a more advanced analysis of requirements and requirement trees:

- Finding similar or relevant requirements.
- Enforce invariants that should be hold. Example: mass or power budget.
<<<

[/SECTION]

[SECTION]
TITLE: Two frontends

[FREETEXT]
There are two frontends for StrictDoc:

1) Text frontend
2) Web frontend

The text frontend is already developed, the web frontend is incubation.
[/FREETEXT]

[REQUIREMENT]
UID: FRONTEND-1-TEXT
TITLE: Text frontend
STATEMENT: >>>
...
<<<

[REQUIREMENT]
UID: FRONTEND-2-WEB
TITLE: Web frontend
STATEMENT: >>>
...
<<<

[/SECTION]

[SECTION]
TITLE: Development team

[FREETEXT]
StrictDoc is a spare time project developed and maintained by a single person
with occasional contributions from the Open Source community.
[/FREETEXT]

[/SECTION]
