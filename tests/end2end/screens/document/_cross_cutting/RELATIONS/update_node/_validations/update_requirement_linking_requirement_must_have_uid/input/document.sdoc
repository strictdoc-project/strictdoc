[DOCUMENT]
TITLE: Document 1

[REQUIREMENT]
TITLE: Requirement #1
STATEMENT: >>>
Requirement statement.
<<<
RATIONALE: >>>
Requirement rationale.
<<<

[REQUIREMENT]
UID: REQ-002
TITLE: Requirement #2
STATEMENT: >>>
Requirement statement.
<<<
RATIONALE: >>>
Requirement rationale.
<<<
