[DOCUMENT]
TITLE: Document 1

[[SECTION]]
TITLE: Section title

[TEXT]
UID: TEXT-NODE-1
STATEMENT: >>>
.. raw:: html

    <pre class="plantuml">
    @startuml
    Alice -> Bob: Hello
    @enduml
    </pre>
<<<

[[/SECTION]]
