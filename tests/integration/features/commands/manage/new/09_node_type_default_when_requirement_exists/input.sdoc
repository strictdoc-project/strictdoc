[DOCUMENT]
TITLE: Test Document

[GRAMMAR]
ELEMENTS:
- TAG: TEXT
  FIELDS:
  - TITLE: UID
    TYPE: String
    REQUIRED: False
  - TITLE: STATEMENT
    TYPE: String
    REQUIRED: True
- TAG: REQUIREMENT
  FIELDS:
  - TITLE: UID
    TYPE: String
    REQUIRED: False
  - TITLE: STATEMENT
    TYPE: String
    REQUIRED: False
- TAG: FEATURE
  FIELDS:
  - TITLE: TITLE
    TYPE: String
    REQUIRED: False

[REQUIREMENT]
UID: REQ-1
STATEMENT: First requirement.
