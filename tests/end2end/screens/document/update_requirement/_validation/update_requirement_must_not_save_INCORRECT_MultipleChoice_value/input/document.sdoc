[DOCUMENT]
TITLE: Document 1

[GRAMMAR]
ELEMENTS:
- TAG: REQUIREMENT
  FIELDS:
  - TITLE: TITLE
    TYPE: String
    REQUIRED: False
  - TITLE: CUSTOM_FIELD
    TYPE: MultipleChoice(A, B, C)
    REQUIRED: True
  - TITLE: STATEMENT
    TYPE: String
    REQUIRED: True

[REQUIREMENT]
TITLE: Requirement title
CUSTOM_FIELD: A
STATEMENT: >>>
Requirement statement.
<<<
