[DOCUMENT]
TITLE: Document 1

[GRAMMAR]
ELEMENTS:
- TAG: SECTION
  PROPERTIES:
    IS_COMPOSITE: True
    VIEW_STYLE: Narrative
  FIELDS:
  - TITLE: MID
    TYPE: String
    REQUIRED: False
  - TITLE: UID
    TYPE: String
    REQUIRED: False
  - TITLE: TITLE
    TYPE: String
    REQUIRED: True
- TAG: REQUIREMENT
  FIELDS:
  - TITLE: UID
    TYPE: String
    REQUIRED: False
  - TITLE: TITLE
    TYPE: String
    REQUIRED: False
  - TITLE: STATEMENT
    TYPE: String
    REQUIRED: True
  RELATIONS:
  - TYPE: Parent

[[SECTION]]
UID: SECTION_NESTING
TITLE: Nesting section

[[SECTION]]
UID: SECTION_SUBNESTING
TITLE: Sub-nesting section

[REQUIREMENT]
UID: REQ-1
TITLE: Requirement title #1
STATEMENT: >>>
Requirement statement #1.
<<<

[[/SECTION]]

[[/SECTION]]

[REQUIREMENT]
UID: REQ-2
TITLE: Requirement title #2
STATEMENT: >>>
Requirement statement #2.
[LINK: SECTION_NESTING]
<<<
RELATIONS:
- TYPE: Parent
  VALUE: REQ-1

[REQUIREMENT]
UID: REQ-3
TITLE: Requirement title #3
STATEMENT: >>>
Requirement statement #3.
[LINK: SECTION_SUBNESTING]
<<<
RELATIONS:
- TYPE: Parent
  VALUE: REQ-1
