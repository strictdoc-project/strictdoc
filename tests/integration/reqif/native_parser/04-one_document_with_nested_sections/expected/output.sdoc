[DOCUMENT]
TITLE: Empty ReqIF document
OPTIONS:
  MARKUP: Text

[SECTION]
TITLE: Section 1

[REQUIREMENT]
UID: REQ_1
STATEMENT: Statement 1.

[SECTION]
TITLE: Section 1.1

[REQUIREMENT]
UID: REQ_1_1
STATEMENT: Statement 1.1.

[SECTION]
TITLE: Section 1.1.1

[REQUIREMENT]
UID: REQ_1_1_1
STATEMENT: Statement 1.1.1

[/SECTION]

[/SECTION]

[/SECTION]

[SECTION]
TITLE: Section 2

[REQUIREMENT]
UID: LLR001
STATEMENT: Statement 2.

[SECTION]
TITLE: Section 2.1

[REQUIREMENT]
UID: LLR001
STATEMENT: Statement 2.1.

[SECTION]
TITLE: Section 2.1.1

[REQUIREMENT]
UID: REQ_2_1_1
STATEMENT: Statement 2.1.1.

[/SECTION]

[/SECTION]

[/SECTION]
