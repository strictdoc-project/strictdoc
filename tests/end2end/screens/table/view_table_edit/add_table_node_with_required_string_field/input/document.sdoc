[DOCUMENT]
TITLE: Document

[GRAMMAR]
ELEMENTS:
- TAG: TASK
  FIELDS:
  - TITLE: UID
    TYPE: String
    REQUIRED: False
  - TITLE: PRIORITY
    TYPE: String
    REQUIRED: True
  - TITLE: TITLE
    TYPE: String
    REQUIRED: False

[TASK]
UID: TASK-1
PRIORITY: High
TITLE: Existing task
