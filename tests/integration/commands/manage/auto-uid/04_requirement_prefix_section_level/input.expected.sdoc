[DOCUMENT]
TITLE: Hello world doc
REQ_PREFIX: DOC-

[SECTION]
TITLE: Section 1.
REQ_PREFIX: LEVEL1-REQ-

[REQUIREMENT]
UID: LEVEL1-REQ-1
STATEMENT: System shall do L1-1.

[REQUIREMENT]
UID: LEVEL1-REQ-2
STATEMENT: System shall do L1-1.

[/SECTION]

[SECTION]
TITLE: Section 2.
REQ_PREFIX: LEVEL2-REQ-

[REQUIREMENT]
UID: LEVEL2-REQ-2
STATEMENT: System shall do L2-1.

[REQUIREMENT]
UID: LEVEL2-REQ-1
STATEMENT: System shall do L2-1.

[/SECTION]
