[DOCUMENT]
TITLE: Hello world doc

[REQUIREMENT]
UID: REQ-1
TITLE: Requirement Title
STATEMENT: Requirement Statement
RELATIONS:
- TYPE: File
  VALUE: file.adb
  ELEMENT: function
  ID: Hello.Hello_World
- TYPE: File
  VALUE: file.adb
  ELEMENT: function
  ID: Hello.Hello_World_2

[REQUIREMENT]
UID: REQ-2
TITLE: Requirement Title #2
STATEMENT: Requirement Statement #2
RELATIONS:
- TYPE: File
  VALUE: file.adb
  FUNCTION: Hello.Hello_World
- TYPE: File
  VALUE: file.adb
  FUNCTION: Hello.Hello_World_2
