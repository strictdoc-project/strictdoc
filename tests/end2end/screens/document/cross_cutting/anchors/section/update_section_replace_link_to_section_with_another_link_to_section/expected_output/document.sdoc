[DOCUMENT]
TITLE: Document 1

[FREETEXT]
Hello world!
[/FREETEXT]

[SECTION]
TITLE: Modified first section title

[FREETEXT]
Modified first section free text.

[LINK: Section-3]
[/FREETEXT]

[/SECTION]

[SECTION]
UID: Section-2
TITLE: Second section

[FREETEXT]
This is a free text of this section.
[/FREETEXT]

[/SECTION]

[SECTION]
UID: Section-3
TITLE: Third section

[FREETEXT]
This is a free text of this section.
[/FREETEXT]

[/SECTION]
