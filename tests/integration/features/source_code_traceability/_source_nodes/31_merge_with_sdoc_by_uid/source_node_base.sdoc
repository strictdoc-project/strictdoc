[DOCUMENT]
MID: c2d4542d5f1741c88dfcb4f68ad7dcbd
TITLE: Requirements from Source Nodes
UID: SRC-NODES-BASE

[GRAMMAR]
ELEMENTS:
- TAG: SECTION
  PROPERTIES:
    IS_COMPOSITE: True
  FIELDS:
  - TITLE: UID
    TYPE: String
    REQUIRED: False
  - TITLE: TITLE
    TYPE: String
    REQUIRED: True
- TAG: REQUIREMENT
  PROPERTIES:
    VIEW_STYLE: Narrative
  FIELDS:
  - TITLE: UID
    TYPE: String
    REQUIRED: False
  - TITLE: MID
    TYPE: String
    REQUIRED: False
  - TITLE: TITLE
    TYPE: String
    REQUIRED: False
  - TITLE: FOO
    TYPE: String
    REQUIRED: False
  - TITLE: BAR
    TYPE: String
    REQUIRED: False
  RELATIONS:
  - TYPE: Parent
  - TYPE: File

[[SECTION]]
TITLE: Merge example.c into static nodes

[REQUIREMENT]
UID: REQ-SOURCE-1
TITLE: TITLE1 from sdoc
FOO: FOO1 text from sdoc
BAR: BAR1 text from sdoc
RELATIONS:
- TYPE: Parent
  VALUE: REQ-1

[REQUIREMENT]
UID: REQ-SOURCE-2
MID: 80cd685d-0e18-44b8-9842-c1863a2eb9ec
TITLE: TITLE2 from sdoc
FOO: FOO2 text from sdoc
BAR: BAR2 text from sdoc
RELATIONS:
- TYPE: Parent
  VALUE: REQ-2

[REQUIREMENT]
UID: REQ-SOURCE-3
TITLE: TITLE3 from sdoc
FOO: FOO3 text from sdoc
BAR: BAR3 text from sdoc
RELATIONS:
- TYPE: Parent
  VALUE: REQ-3

[[/SECTION]]
