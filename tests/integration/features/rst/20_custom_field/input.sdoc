[DOCUMENT]
TITLE: Test Document

[GRAMMAR]
ELEMENTS:
- TAG: REQUIREMENT
  FIELDS:
  - TITLE: UID
    TYPE: String
    REQUIRED: True
  - TITLE: TAGS
    TYPE: String
    REQUIRED: False
  - TITLE: CRITICALITY
    TYPE: String
    REQUIRED: False
  - TITLE: LEVEL
    TYPE: String
    REQUIRED: False
  - TITLE: STATUS
    TYPE: String
    REQUIRED: False
  - TITLE: TITLE
    TYPE: String
    REQUIRED: False
  - TITLE: STATEMENT
    TYPE: String
    REQUIRED: False
  - TITLE: RATIONALE
    TYPE: String
    REQUIRED: False
  - TITLE: COMMENT
    TYPE: String
    REQUIRED: False
  - TITLE: PUB_REFS
    TYPE: String
    REQUIRED: False
  - TITLE: VERIFICATION
    TYPE: String
    REQUIRED: False

[REQUIREMENT]
UID: A-1
TAGS: has_comment, has_rationale
CRITICALITY: High
STATEMENT: >>>
the foo must bar
<<<
RATIONALE: >>>
If the foo did not bar then it might instead baz, which must be avoided at all costs.
<<<
COMMENT: >>>
A bazzing foo is dangerous because of the uncontrolled range of interaction of the baz with other foos.
<<<
PUB_REFS: >>>
References

1

2
<<<
VERIFICATION: >>>
Very detailed verification step;

With multiple paragraphs
<<<
