[DOCUMENT]
TITLE: Test document

[GRAMMAR]
ELEMENTS:
- TAG: REQUIREMENT
  FIELDS:
  - TITLE: CHOICE_FIELD
    TYPE: MultipleChoice(A, B, C, D)
    REQUIRED: True
  - TITLE: STATEMENT
    TYPE: String
    REQUIRED: False

[REQUIREMENT]
CHOICE_FIELD: TBD

[REQUIREMENT]
CHOICE_FIELD: TBC

[REQUIREMENT]
CHOICE_FIELD: A, TBD
