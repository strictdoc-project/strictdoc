[DOCUMENT]
TITLE: Hello world doc
PREFIX: DOC-

[GRAMMAR]
ELEMENTS:
- TAG: TEXT
  FIELDS:
  - TITLE: UID
    TYPE: String
    REQUIRED: False
  - TITLE: STATEMENT
    TYPE: String
    REQUIRED: True
- TAG: SECTION
  PROPERTIES:
    IS_COMPOSITE: True
    PREFIX: None
  FIELDS:
  - TITLE: MID
    TYPE: String
    REQUIRED: False
  - TITLE: UID
    TYPE: String
    REQUIRED: False
  - TITLE: TITLE
    TYPE: String
    REQUIRED: False
- TAG: REQUIREMENT
  PROPERTIES:
    PREFIX: LEVEL1-REQ-
  FIELDS:
  - TITLE: MID
    TYPE: String
    REQUIRED: False
  - TITLE: UID
    TYPE: String
    REQUIRED: False
  - TITLE: STATEMENT
    TYPE: String
    REQUIRED: False

[[SECTION]]
TITLE: Section 1

[REQUIREMENT]
UID: LEVEL1-REQ-1
STATEMENT: System shall do L1-1.

[REQUIREMENT]
UID: LEVEL1-REQ-2
STATEMENT: System shall do L1-1.

[[/SECTION]]
