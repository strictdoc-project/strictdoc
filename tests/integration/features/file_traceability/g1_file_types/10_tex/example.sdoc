[DOCUMENT]
TITLE: Example: Traceability between requirements and source files

[REQUIREMENT]
UID: REQ-001
REFS:
- TYPE: File
  VALUE: file.tex
TITLE: Whole file reference
STATEMENT: This requirement references the whole file.

[REQUIREMENT]
UID: REQ-002
REFS:
- TYPE: File
  VALUE: file.tex
TITLE: Source range reference
STATEMENT: This requirement references a range in the file.

[REQUIREMENT]
UID: REQ-003
REFS:
- TYPE: File
  VALUE: file.tex
TITLE: Source range reference
STATEMENT: This requirement references a range in the file.
