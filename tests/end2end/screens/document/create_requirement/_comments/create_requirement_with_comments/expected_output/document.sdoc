[DOCUMENT]
TITLE: Document 1

[REQUIREMENT]
UID: REQ-001
TITLE: Requirement title #1
STATEMENT: >>>
Requirement statement #1.
<<<
RATIONALE: >>>
Requirement rationale #1.
<<<
COMMENT: >>>
Comment #1
<<<
COMMENT: >>>
Comment #2
<<<
COMMENT: >>>
Comment #3
<<<
