[DOCUMENT]
TITLE: Test document

[[SECTION]]
TITLE: New section title

[[SECTION]]
TITLE: Section title

[REQUIREMENT]
TITLE: Requirement title
STATEMENT: Requirement statement.

[[/SECTION]]

[[/SECTION]]
