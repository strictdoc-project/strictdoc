[DOCUMENT]
TITLE: Hello world doc
SPECIAL_FIELDS:
- NAME: ECSS_VERIFICATION
  TYPE: String
- NAME: ECSS_COMPLIANCE
  TYPE: String

[REQUIREMENT]
SPECIAL_FIELDS:
  ECSS_VERIFICATION: R,A,I,T
  ECSS_COMPLIANCE: Compliant
