[DOCUMENT]
TITLE: Requirements
UID: SDOC_REQ
OPTIONS:
  REQUIREMENT_STYLE: Inline

[GRAMMAR]
ELEMENTS:
- TAG: REQUIREMENT
  FIELDS:
  - TITLE: UID
    TYPE: String
    REQUIRED: False
  - TITLE: TITLE
    TYPE: String
    REQUIRED: True
  - TITLE: STATEMENT
    TYPE: String
    REQUIRED: True
  - TITLE: RATIONALE
    TYPE: String
    REQUIRED: False
  - TITLE: COMMENT
    TYPE: String
    REQUIRED: False
  RELATIONS:
  - TYPE: Parent
  - TYPE: Parent
    ROLE: Refines
  - TYPE: Parent
    ROLE: Implements
  - TYPE: File

[FREETEXT]
This document is a collection of high-level requirements for StrictDoc as well as some of its middle-level requirements. The existing requirements set is pending a proper functional decomposition/partitioning following the creation of bidirectional traces between the requirements and StrictDoc's source code.
[/FREETEXT]

[SECTION]
TITLE: High-level requirements

[REQUIREMENT]
UID: SDOC-HIGH-REQS-MANAGEMENT
TITLE: Requirements management
STATEMENT: >>>
StrictDoc shall enable requirements management.
<<<
REFS:
- TYPE: Parent
  VALUE: GOAL-1-TOOL-SUPPORT
  ROLE: Refines

[REQUIREMENT]
UID: SDOC-HIGH-DATA-MODEL
TITLE: Data model
STATEMENT: >>>
StrictDoc shall be based on a data model.
<<<

[REQUIREMENT]
TITLE: Command-line interface
STATEMENT: StrictDoc shall provide a command-line interface.

[REQUIREMENT]
TITLE: Graphical user interface
STATEMENT: >>>
StrictDoc shall provide a Graphical User Interface (GUI).
<<<
COMMENT: >>>
Several trade-offs to consider:

- Desktop vs Web. Rather web-based, i.e. Python backend and JS frontend, but which technology?
- Still keep the current behavior of a statically generated website?
<<<

[REQUIREMENT]
TITLE: Statically generated website
STATEMENT: >>>
StrictDoc shall allow generating requirements content to static HTML website.
<<<

[SECTION]
TITLE: Platform support

[REQUIREMENT]
TITLE: macOS support
STATEMENT: StrictDoc shall work on macOS systems.

[REQUIREMENT]
TITLE: Linux support
STATEMENT: StrictDoc shall work on Linux systems.

[REQUIREMENT]
TITLE: Windows support
STATEMENT: StrictDoc shall work on Windows systems.

[/SECTION]

[REQUIREMENT]
UID: SDOC-HIGH-VALIDATION
TITLE: Requirements validation
STATEMENT: StrictDoc shall allow validation of requirement documents.

[REQUIREMENT]
TITLE: Requirements text format
STATEMENT: StrictDoc shall allow storage of requirements in a plain-text human readable form.

[REQUIREMENT]
TITLE: Linking requirements
STATEMENT: StrictDoc shall support linking requirements to each other.

[REQUIREMENT]
TITLE: Scalability
STATEMENT: StrictDoc shall allow working with large documents and document trees containing at least 10000 requirement items.

[REQUIREMENT]
UID: SDOC-HIGH-REQS-TRACEABILITY
TITLE: Traceability
STATEMENT: StrictDoc shall support traceability of requirements.

[REQUIREMENT]
TITLE: Visualization
STATEMENT: StrictDoc shall provide means for visualization of requirement documents.

[REQUIREMENT]
TITLE: Open source software
STATEMENT: StrictDoc shall always be free and open source software.

[/SECTION]

[SECTION]
TITLE: Data model

[REQUIREMENT]
UID: SDOC-DM-MODEL
TITLE: Modeling capability
STATEMENT: StrictDoc's Data Model shall accommodate for maximum possible standard requirement document formats.
COMMENT: >>>
Examples of standard requirements documents include but are not limited to:

- Non-nested requirement lists split by categories
  (e.g., Functional Requirements, Interface Requirements, Performance Requirements, etc.)
<<<
REFS:
- TYPE: Parent
  VALUE: SDOC-HIGH-REQS-MANAGEMENT
- TYPE: Parent
  VALUE: SDOC-HIGH-DATA-MODEL

[SECTION]
TITLE: Project

[REQUIREMENT]
TITLE: Project concept
STATEMENT: >>>
StrictDoc shall support the "Project" concept.
<<<
RATIONALE: >>>
A project is a top-level entity. The project groups SDoc documents into a single project documentation tree.
<<<

[REQUIREMENT]
TITLE: Project title
STATEMENT: >>>
Project shall have a "Title" property.
<<<
COMMENT: >>>
Currently, the project title aspect is not part of the SDoc grammar. It is
simply specified via the ``--project-title`` command-line option. This might
change when the project title will be configured as part of the project-level
config file (TOML or SDoc-like grammar).
<<<

[/SECTION]

[SECTION]
TITLE: Document

[REQUIREMENT]
TITLE: Document
STATEMENT: >>>
StrictDoc Data Model shall support the "Document" concept.
<<<

[/SECTION]

[SECTION]
TITLE: Section

[REQUIREMENT]
TITLE: Section concept
STATEMENT: >>>
StrictDoc Data Model shall support the "Section" concept.
<<<

[/SECTION]

[SECTION]
TITLE: Requirement

[REQUIREMENT]
TITLE: Requirement concept
STATEMENT: >>>
StrictDoc Data Model shall support the "Requirement" concept.
<<<

[REQUIREMENT]
TITLE: Statement
STATEMENT: Requirement item shall have a statement.

[SECTION]
TITLE: UID identifier

[REQUIREMENT]
TITLE: UID identifier
STATEMENT: Requirement item may have an UID identifier.

[REQUIREMENT]
TITLE: UID identifier format
STATEMENT: StrictDoc shall not impose any restrictions on the UID field format.
COMMENT: >>>
Conventions used for requirement UIDs can be very different. And there seems to
be no way to define a single rule.

Some examples:

- FUN-003
- cES1008, cTBL6000.1 (NASA cFS)
- Requirements without a number, e.g. SDOC-HIGH-DATA-MODEL (StrictDoc)
- SAVOIR.OBC.PM.80 (SAVOIR)
<<<

[/SECTION]

[REQUIREMENT]
TITLE: Title
STATEMENT: Requirement item may have an title.

[REQUIREMENT]
TITLE: References
STATEMENT: Requirement item may have one or more references.

[REQUIREMENT]
TITLE: Comments
STATEMENT: Requirement item may have one or more comments.

[REQUIREMENT]
TITLE: Special fields
STATEMENT: StrictDoc shall support customization of the default Requirement's grammar with special fields.
COMMENT: >>>
Examples:

- RAIT compliance fields (Review of design, analysis, inspection, testing)
- Automotive Safety Integrity Level level (ASIL).
<<<

[/SECTION]

[SECTION]
TITLE: Composite requirement

[REQUIREMENT]
TITLE: Composite requirement concept
STATEMENT: >>>
StrictDoc Data Model shall support the "Composite requirement" concept.
<<<

[/SECTION]

[SECTION]
TITLE: Links

[REQUIREMENT]
TITLE: Links
STATEMENT: StrictDoc's data model shall support linking document content nodes to each other.

[REQUIREMENT]
TITLE: Parent links
STATEMENT: StrictDoc's data model shall support linking a requirement to another requirement using PARENT link.

[/SECTION]

[/SECTION]

[SECTION]
TITLE: SDoc file format

[REQUIREMENT]
UID: SDOC-FMT-PRIMARY
TITLE: Primary text implementation
STATEMENT: The SDoc format shall support encoding the Strict Doc Data Model in a plain-text human readable form.
REFS:
- TYPE: Parent
  VALUE: SDOC-DM-MODEL

[SECTION]
TITLE: Grammar

[REQUIREMENT]
UID: SDOC-FMT-GRAMMAR
TITLE: Grammar
STATEMENT: The SDoc format shall be based on a fixed grammar.
REFS:
- TYPE: Parent
  VALUE: SDOC-HIGH-DATA-MODEL
- TYPE: File
  VALUE: strictdoc/backend/sdoc/grammar/grammar.py

[REQUIREMENT]
TITLE: No indentation
STATEMENT: The SDoc grammar's building blocks shall not allow any indentation.
COMMENT: >>>
Rationale: Adding indentation to any of the fields does not scale well when the
documents have deeply nested section structure as well as when the size of the
paragraphs becomes sufficiently large. Keeping every keyword like [REQUIREMENT]
or [COMMENT] with no indentation ensures that one does not have to think about
possible indentation issues.
<<<

[/SECTION]

[REQUIREMENT]
TITLE: Type safety
STATEMENT: The SDoc format shall allow type-safe encoding of requirement documents.

[/SECTION]

[SECTION]
TITLE: Export and import capabilities

[SECTION]
TITLE: General

[REQUIREMENT]
TITLE: Generated file names
STATEMENT: >>>
StrictDoc shall preserve original document file names when generating to all
export formats.
<<<

[/SECTION]

[SECTION]
TITLE: HTML Export

[REQUIREMENT]
TITLE: Single document: Normal form
STATEMENT: StrictDoc shall export single document pages in a normal document-like form.

[REQUIREMENT]
TITLE: Single document: Tabular form
STATEMENT: StrictDoc shall export single document pages in a tabular form.

[REQUIREMENT]
TITLE: Single document: 1-level traceability
STATEMENT: StrictDoc shall export 1-level traceability document.
REFS:
- TYPE: Parent
  VALUE: SDOC-HIGH-REQS-TRACEABILITY

[REQUIREMENT]
TITLE: Single document: Deep traceability
STATEMENT: StrictDoc shall export deep traceability document.
REFS:
- TYPE: Parent
  VALUE: SDOC-HIGH-REQS-TRACEABILITY

[REQUIREMENT]
TITLE: Left panel: Table of contents
STATEMENT: StrictDoc shall export all HTML pages with Table of Contents.

[/SECTION]

[SECTION]
TITLE: PDF Export

[REQUIREMENT]
TITLE: Sphinx documentation generator
STATEMENT: StrictDoc shall support exporting documents to Sphinx/RST format.

[/SECTION]

[REQUIREMENT]
UID: SDOC-GEN-EXCEL-EXPORT
TITLE: Excel Export
STATEMENT: StrictDoc shall support exporting documents to Excel format.
REFS:
- TYPE: File
  VALUE: strictdoc/backend/excel/export/excel_generator.py

[REQUIREMENT]
TITLE: ReqIF import/export
STATEMENT: StrictDoc shall support the ReqIF format.

[/SECTION]

[SECTION]
TITLE: Validation

[REQUIREMENT]
UID: SDOC-VALIDATION-UNIQUE-UID
TITLE: Uniqueness of UID identifiers in a document tree
STATEMENT: StrictDoc shall ensure that each UID used in a document tree is unique.
COMMENT: This is implemented but the error message shall be made more readable.
REFS:
- TYPE: Parent
  VALUE: SDOC-HIGH-VALIDATION

[REQUIREMENT]
UID: SDOC-VALIDATION-NO-CYCLES
TITLE: No cycles in a document tree
STATEMENT: >>>
StrictDoc shall ensure that no requirements in document tree reference each other.
<<<
REFS:
- TYPE: Parent
  VALUE: SDOC-HIGH-VALIDATION
- TYPE: File
  VALUE: strictdoc/core/tree_cycle_detector.py
- TYPE: File
  VALUE: strictdoc/core/traceability_index_builder.py

[REQUIREMENT]
UID: SDOC-VALIDATION-VALID-HTML
TITLE: Valid HTML markup
STATEMENT: StrictDoc's HTML export tests shall validate the generated HTML markup.
COMMENT: First candidate: Table of contents and its nested ``<ul>/<li>`` items.
REFS:
- TYPE: Parent
  VALUE: SDOC-HIGH-VALIDATION

[/SECTION]

[SECTION]
TITLE: Traceability and coverage

[REQUIREMENT]
TITLE: Linking with implementation artifacts
STATEMENT: StrictDoc shall support linking requirements to files.

[REQUIREMENT]
TITLE: Validation: Broken links from requirements to source files
STATEMENT: >>>
StrictDoc shall warn a user about all requirements whose links reference source
files that do not exist.
<<<

[REQUIREMENT]
TITLE: Validation: Broken links from source files to requirements
STATEMENT: >>>
StrictDoc shall warn a user about all source files whose links reference
requirements that do not exist.
<<<

[REQUIREMENT]
TITLE: Requirements coverage
STATEMENT: StrictDoc shall generate requirements coverage information.
COMMENT: >>>
Requirements coverage screen shows how requirements are linked with source files.
<<<

[REQUIREMENT]
TITLE: Source coverage
STATEMENT: StrictDoc shall generate source coverage information.
COMMENT: >>>
Source coverage screen shows how source files are linked with requirements.
<<<

[/SECTION]

[SECTION]
TITLE: Web frontend requirements

[FREETEXT]
TBD
[/FREETEXT]

[/SECTION]

[SECTION]
TITLE: Implementation requirements

[REQUIREMENT]
UID: SDOC-IMPL-PARAL
TITLE: Parallelization
STATEMENT: StrictDoc shall enable parallelization of the time-consuming parts of the code.
REFS:
- TYPE: File
  VALUE: strictdoc/helpers/parallelizer.py

[REQUIREMENT]
UID: SDOC-IMPL-INCREMENTAL
TITLE: Incremental generation
STATEMENT: StrictDoc shall enable incremental generation of the documents.
COMMENT: >>>
When exporting documentation tree, StrictDoc shall regenerate only changed
documents and files.
<<<

[/SECTION]
