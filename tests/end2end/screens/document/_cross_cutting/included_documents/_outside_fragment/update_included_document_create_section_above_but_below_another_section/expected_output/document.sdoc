[DOCUMENT]
TITLE: Document 1

[TEXT]
STATEMENT: >>>
Hello world!
<<<

[[SECTION]]
TITLE: Section Foobar

[[/SECTION]]

[[SECTION]]
TITLE: Section created by this test

[[/SECTION]]

[DOCUMENT_FROM_FILE]
FILE: fragment.sdoc
