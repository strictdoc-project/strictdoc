[DOCUMENT]
NAME: Hello world doc
SPECIAL_FIELDS:
- NAME: OWNER
  TYPE: String
- NAME: PRIORITY
  TYPE: String

[REQUIREMENT]
UID: REQ-001
TITLE: Title #1
STATEMENT: Statement #1

[REQUIREMENT]
UID: REQ-002
SPECIAL_FIELDS:
  OWNER: Some Owner
  PRIORITY: High
REFS:
- TYPE: Parent
  VALUE: REQ-001
TITLE: Title #2
STATEMENT: Statement #2

[REQUIREMENT]
UID: REQ-003
REFS:
- TYPE: Parent
  VALUE: REQ-002
TITLE: Title #3
STATEMENT: Statement #3
