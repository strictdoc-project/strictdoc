[DOCUMENT]
TITLE: Hello world doc

[[SECTION]]
TITLE: Section with anchor

[TEXT]
STATEMENT: >>>
Anchors start.

[ANCHOR: AD1]

1) AD1. Software user manual.

[ANCHOR: AD2, Software requirements specification]

2) AD2. Software requirements specification.

[ANCHOR: Interface_Control_Document]

3) AD3. Interface Control Document.

Anchors end.
<<<

[TEXT]
STATEMENT: >>>
[ANCHOR: AD4]

1) AD4. Threat Model.

[ANCHOR: AD5, Software Tests]

2) AD5. Software Tests.

[ANCHOR: Supplemental Guide]

3) AD6. Supplemental Guide.

Anchors end.
<<<

[[/SECTION]]
