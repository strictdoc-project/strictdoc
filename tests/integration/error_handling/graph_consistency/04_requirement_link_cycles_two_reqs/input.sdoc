[DOCUMENT]
TITLE: Doc 1

[REQUIREMENT]
UID: REQ-001
REFS:
- TYPE: Parent
  VALUE: REQ-002
STATEMENT: Hello world 1

[REQUIREMENT]
UID: REQ-002
REFS:
- TYPE: Parent
  VALUE: REQ-001
STATEMENT: Hello world 2
