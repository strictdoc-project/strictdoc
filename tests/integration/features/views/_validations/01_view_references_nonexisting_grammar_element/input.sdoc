[DOCUMENT]
TITLE: Test Document
OPTIONS:
  REQUIREMENT_STYLE: Inline
  DEFAULT_VIEW: PRINT_VIEW
VIEWS:
- ID: PRINT_VIEW
  NAME: Print view
  TAGS:
  - OBJECT_TYPE: NON_EXISTING_OBJECT
    VISIBLE_FIELDS:
    - NAME: UID
      PLACEMENT: XYZ
    - NAME: STATEMENT
    - NAME: RATIONALE
  - OBJECT_TYPE: ASSUMPTION
    VISIBLE_FIELDS:
    - NAME: UID
      PLACEMENT: XYZ
    - NAME: STATEMENT
