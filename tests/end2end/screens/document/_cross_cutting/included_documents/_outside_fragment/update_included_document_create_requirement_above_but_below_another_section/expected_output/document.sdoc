[DOCUMENT]
TITLE: Document 1

[[SECTION]]
TITLE: Section Foobar

[[/SECTION]]

[REQUIREMENT]
UID: REQ-1
TITLE: Requirement title
STATEMENT: >>>
Requirement statement.
<<<

[DOCUMENT_FROM_FILE]
FILE: fragment.sdoc
