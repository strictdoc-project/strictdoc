[DOCUMENT]
TITLE: [L1] Requirements Tool concept
REQ_PREFIX: SDOC-RMC-

[SECTION]
UID: SECTION-RTC-Requirements-management
TITLE: Requirements management

[REQUIREMENT]
UID: SDOC-RMC-20
STATUS: Active
TITLE: Manage requirements (CRUD)
STATEMENT: >>>
The Requirements Tool shall enable the main requirements management operations:

- Create a requirement
- Read / view / browse a requirement
- Update / edit a requirement
- Delete a requirement.
<<<
RATIONALE: >>>
The CRUD operations are at the core of the requirements management.
<<<

[REQUIREMENT]
UID: SDOC-RMC-21
STATUS: Active
TITLE: Requirements and specifications (plain, non-nested vs deeply nested)

[REQUIREMENT]
UID: SDOC-RMC-32
STATUS: Active
TITLE: Support large requirements sets
STATEMENT: The Tool shall support requirements sets of up to 10000+ requirements.

[REQUIREMENT]
UID: SDOC-RMC-37
STATUS: Active
TITLE: Requirements writing best practice

[/SECTION]

[SECTION]
UID: SECTION-RTC-Documentation-management
TITLE: Documentation management

[REQUIREMENT]
UID: SDOC-RMC-22
STATUS: Active
TITLE: Manage documents (CRUD)

[REQUIREMENT]
UID: SDOC-RMC-23
STATUS: Active
TITLE: Support variety of document types
STATEMENT: >>>
The Requirements Tool shall support a variety of document types used by the industries. The variety comes from:

- Supporting flexible documentation structures, e.g., non-nested vs. deeply nested.
- Supporting custom fields used by different industries (the criticality levels in various industries, RAIT in aerospace, status/workflow fields, etc.)
- Supporting a rich set of visualization mechanisms.

NOTE: Examples of document types include:

- Requirements specification
- Design document / architecture description document
- Interface control document / API reference
- User manual
- Development plan, systems engineering plan, management plan
- Standard (e.g., ECSS or ISO 26262).
<<<

[REQUIREMENT]
UID: SDOC-RMC-31
STATUS: Active
TITLE: Support large project trees
STATEMENT: The Tool shall support project trees and documentation packages of up to 100 documents.

[REQUIREMENT]
UID: SDOC-RMC-35
STATUS: Active
TITLE: Support documentation control (meta info and signatures)

[/SECTION]

[SECTION]
UID: SECTION-RTC-Documentation-consistency
TITLE: Documentation consistency

[FREETEXT]
- No (or less) run-away documentation
- Reduce documentation hazards
- Keep documents up-to-date
[/FREETEXT]

[REQUIREMENT]
UID: SDOC-RMC-33
STATUS: Active
TITLE: Document versioning

[REQUIREMENT]
UID: SDOC-RMC-34
STATUS: Active
TITLE: Requirement versioning

[REQUIREMENT]
UID: SDOC-RMC-7
STATUS: Active
TITLE: Maintain consistency of requirements database

[REQUIREMENT]
UID: SDOC-RMC-38
STATUS: Active
TITLE: Change management
STATEMENT: >>>
The Requirements Tool shall provide capabilities for change management:

- Visualizing changes between project tree versions.
- Visualizing changes between document versions.
- Visualizing the impact that a changed requirement has on a project tree.
<<<

[/SECTION]

[SECTION]
UID: SECTION-RTC-Support-engineering-activities
TITLE: Support engineering activities

[FREETEXT]
- Assist workflows with project requirements and documentations
- Integrate with existing workflows
[/FREETEXT]

[REQUIREMENT]
UID: SDOC-RMC-42
STATUS: Active
TITLE: Document- and table-based workflow

[REQUIREMENT]
UID: SDOC-RMC-1
STATUS: Active
TITLE: Requirements analysis and prototyping

[REQUIREMENT]
UID: SDOC-RMC-39
STATUS: Active
TITLE: Requirements compliance identification
STATEMENT: >>>
The Requirements Tool shall provide capabilities for Compliance management, traceability and justification.
<<<

[REQUIREMENT]
UID: SDOC-RMC-2
STATUS: Active
TITLE: Requirements implementation
STATEMENT: >>>
The Requirements Tool shall provide capabilities for software development according to requirements.

NOTE: A contribution of a requirements tool to software engineering can be:

- Assisting software engineers in implementing requirements in source code.
- Making links between requirements and source code implementation units, e.g., files, functions, code fragments.
- Linking source code implementation units to requirements using special markers left in source code.
<<<

[REQUIREMENT]
UID: SDOC-RMC-3
STATUS: Active
TITLE: Requirements verification workflow (RAIT)

[REQUIREMENT]
UID: SDOC-RMC-56
STATUS: Active
TITLE: Configuration management
STATEMENT: >>>
The Requirements Tool shall provide capabilities for Configuration Management:

- Versioning documentation releases.
- Historical view of the documentation (e.g., travel back in time).
<<<

[REQUIREMENT]
UID: SDOC-RMC-41
STATUS: Active
TITLE: Reporting

[REQUIREMENT]
UID: SDOC-RMC-12
STATUS: Active
TITLE: Collaborate on requirements

[REQUIREMENT]
UID: SDOC-RMC-13
STATUS: Active
TITLE: Exchange requirements

[REQUIREMENT]
UID: SDOC-RMC-17
STATUS: Active
TITLE: Formal reviews
STATEMENT: >>>
The Requirements Tool shall support the formal reviews activities:

- Formal review of documentation
- Walkthroughs, inspections
- Version control of delivered documentation packages
- Assessment of progress reports achieved.
<<<

[REQUIREMENT]
UID: SDOC-RMC-18
STATUS: Active
TITLE: Interoperability with industry standards

[REQUIREMENT]
UID: SDOC-RMC-57
STATUS: Active
TITLE: Integration between distinct projects requirements trees
STATEMENT: >>>
The Requirements Tool shall provide capabilities for integrating project requirements trees with each other.

NOTE: Examples of integration:

- An embedded software project has its own requirements. The developers want to integrate a requirements subtree of another product that is integrated to the parent project as an off-the-shelf solution.
<<<

[/SECTION]

[SECTION]
UID: SECTION-RTC-Inclusive-requirements-collaboration
TITLE: Inclusive requirements collaboration

[SECTION]
UID: SECTION-RTC-General-considerations
TITLE: General considerations

[REQUIREMENT]
UID: SDOC-RMC-8
STATUS: Active
TITLE: General usability
STATEMENT: >>>
The Requirements Tool shall be accessible to a broad spectrum of users.

NOTE: Factors to consider:

- The cost of a tool.
- The easy of installation.
- The availability of a graphical user interface.
- The availability of a programmatic access to the functions of a tool.
- The interoperability of the tool with other tools.
<<<
RATIONALE: >>>
A tool that can be used by a large number of people simplifies its adoption and allows more users to work with documentation and requirements.
<<<

[REQUIREMENT]
UID: SDOC-RMC-9
STATUS: Active
TITLE: Easy user experience
STATEMENT: >>>
The Requirements Tool shall provide a smooth user experience.

NOTE: Documentation and requirements management are composite activities that consist of several types of repetitive tasks. A requirements tool user experience should assist in automating these tasks as far as possible and make the overall workflow efficient and precise.
<<<

[REQUIREMENT]
UID: SDOC-RMC-54
STATUS: Active
TITLE: Support projects with a large number of users
STATEMENT: >>>
The Requirements Tool shall be capable of supporting a large number of users.
<<<
RATIONALE: >>>
Many documentation and requirements projects involve large groups of people. The requirements tool should not become a bottleneck when a number of users grows.
<<<

[/SECTION]

[SECTION]
UID: SECTION-RTC-Target-audience
TITLE: Target audience

[REQUIREMENT]
UID: SDOC-RMC-36
STATUS: Active
TITLE: Engineering professionals
STATEMENT: >>>
- Graphical user interface
<<<

[REQUIREMENT]
UID: SDOC-RMC-11
STATUS: Active
TITLE: Software engineers
COMMENT: >>>
The tool is close to software engineering workflow, i.e., it has edges to
software version control, software IDEs, source code, etc.
<<<

[REQUIREMENT]
UID: SDOC-RMC-43
STATUS: Active
TITLE: Management
COMMENT: >>>
- Graphical user interface
- Project overview (1000ft)
- Project statistics
- Progress reports
- Compliance and traceability
<<<

[REQUIREMENT]
UID: SDOC-RMC-44
STATUS: Active
TITLE: General audience
COMMENT: >>>
- Graphical user interface
<<<

[/SECTION]

[/SECTION]

[SECTION]
UID: SECTION-RTC-Usability-installation-and-usage
TITLE: Usability, installation and usage

[REQUIREMENT]
UID: SDOC-RMC-45
STATUS: Active
TITLE: Individual use (home PC)
STATEMENT: >>>
The Requirements Tool shall be usable on the normal personal computers, e.g., do not require a special cloud deployment.
<<<

[REQUIREMENT]
UID: SDOC-RMC-14
STATUS: Active
TITLE: Server-based deployments (IT-friendly setup)
STATEMENT: >>>
The Requirements Tool shall be deployable to the network of computers, e.g., provide a server instance.
<<<
COMMENT: >>>
Scaling from smaller setups (e.g., Raspberry PI in an office network) to
larger in-house and cloud-base installations.
<<<

[REQUIREMENT]
UID: SDOC-RMC-46
STATUS: Active
TITLE: Requirements database
STATEMENT: >>>
The Requirements Tool shall store documentation and requirements data in a database.
<<<
RATIONALE: >>>
A database allows:

- Persistent storage of documentation/requirements data
- Versioning
- Backups
- Exchange of information and access of the same database by multiple users.
<<<

[REQUIREMENT]
UID: SDOC-RMC-47
STATUS: Active
TITLE: Programming access via API (Web)
STATEMENT: >>>
The Requirements Tool shall provide a Web API interface.
<<<
RATIONALE: >>>
Besides a direct access to the tool's source code, accessing an API deployed to a server provides additional capabilities for getting and manipulating requirements/documentation content.
<<<

[REQUIREMENT]
UID: SDOC-RMC-48
STATUS: Active
TITLE: Programming access via API (SDK)
STATEMENT: >>>
The Requirements Tool shall provide a Software Development Kit (SDK) that allows customization of the Requirements Tool functions.

NOTE: An SDK provides access to the API of the Requirements Tool. Examples of functions that may be used by the users of the tool:

- Custom import/export functions to/from various requirements/documentation formats.
- Implement custom visualization functions.
- Implement integration with other tools.
<<<
RATIONALE: >>>
A SDK allows a software engineer to extend the Requirements Tool capabilities.
<<<

[REQUIREMENT]
UID: SDOC-RMC-49
STATUS: Active
TITLE: Programmatic access to requirements data
STATEMENT: >>>
The Requirements Tool shall provide programmatic access to requirements data.
<<<
RATIONALE: >>>
When the requirements data is accessible by a user directly, it is possible to exchange the data or implement additional scripting procedures.
<<<

[/SECTION]

[SECTION]
UID: SECTION-RTC-Open-requirements-software
TITLE: Open requirements software

[REQUIREMENT]
UID: SDOC-RMC-50
STATUS: Active
TITLE: Free software (freedom and beer, take two)

[REQUIREMENT]
UID: SDOC-RMC-10
STATUS: Active
TITLE: Barrier-free access to requirements data (easy in, easy out)

[REQUIREMENT]
UID: SDOC-RMC-51
STATUS: Active
TITLE: Direct access to the tool source code

[REQUIREMENT]
UID: SDOC-RMC-52
STATUS: Active
TITLE: Educational value
COMMENT: >>>
- Showcase requirements documents setups
- Spread the best (better) practices
<<<

[/SECTION]

[SECTION]
UID: SECTION-RTC-Development-process
TITLE: Development process

[REQUIREMENT]
UID: SDOC-RMC-25
STATUS: Active
TITLE: Requirements engineering
STATEMENT: >>>
The Requirements Tool's development process shall include the Requirements Tool's own requirements engineering.
<<<
RATIONALE: >>>
A requirements tool is not a trivial project. A clear set of requirements for the developed tool helps to structure the development and communicate the functions of the tool to the developers and the users of the tool.
<<<

[REQUIREMENT]
UID: SDOC-RMC-53
STATUS: Active
TITLE: Self-hosted requirements
STATEMENT: >>>
The Requirements Tool's requirements shall be developed using the Requirements Tool.
<<<
RATIONALE: >>>
While not strictly necessary, developing the requirements for the tool using the tool itself aids developers in test-driving its functionality during the requirement development phase. Moreover, having the tool host its own requirements provides a tangible and dynamic illustration of how the tool can be employed for crafting requirements documentation.
<<<

[REQUIREMENT]
UID: SDOC-RMC-26
STATUS: Active
TITLE: Test coverage
STATEMENT: >>>
The Requirements Tool's development process shall ensure:

- A testability of the tool
- The highest possible coverage of the tool's code by test
- Usage of modern testing methods to ensure adequate coverage of the tool's functions (e.g., command-line interface, web interface, smallest units of code, etc.).
<<<
RATIONALE: >>>
The presence of tests, the adequate selection of test methods and a high test coverage are preconditions for a high quality of the requirements tool.
<<<

[REQUIREMENT]
UID: SDOC-RMC-24
STATUS: Active
TITLE: Tool qualification
STATEMENT: >>>
The Requirements Tool's development process shall ensure that the tool can be qualified for the use in critical product developments as required by the rigorous technical standards (e.g., EN IEC 61508).
<<<
RATIONALE: >>>
Many project developments require a qualification of the tools used during the development. A requirements tool is one of the critical tools that affect the project development. If a requirement tool is developed to higher standards of quality, it simplifies the argument of bringing the tool forward and using it in a particular project.
<<<

[/SECTION]

[SECTION]
UID: SECTION-RTC-Appendix-A-Document-archetypes
TITLE: Appendix A: Document archetypes

[FREETEXT]
StrictDoc shall support the following document archetypes: **requirements document**
and **specification** document. For both archetypes, StrictDoc shall further
support the following options.

.. list-table:: Table: Requirements and specification document
   :widths: 20 40 40
   :header-rows: 1

   * -
     - Requirements document
     - Specification document
   * - Examples
     - Most typical: requirements lists split by categories (e.g., Functional
       Requirements, Interface Requirements, Performance Requirements, etc.)
     - Often: a standard document
   * - Structure
     - Not nested or not too deeply nested
     - Nested
   * - Visual presentation
     - Requirements are often presented as table cells. Cells can be standalone
       or the whole section or document can be a long table with cells.
     - Requirements are rather presented as header + text
   * - Unique requirement identifiers (UID)
     - Most always
     - - Present or not
       - **NOT SUPPORTED YET:** Can be missing, the chapter headers are used instead.
         The combination "Number + Title" becomes a reference-able identifier.
         A possible intermediate solution when modeling such a document is to
         make the UIDs map to the section number.
   * - Requirement titles
     - - Often
       - **NOT SUPPORTED YET:** But maybe absent (ex: NASA cFS SCH). If absent,
         the grouping is provided by sections.
     - Requirement titles are most often section titles
   * - Real-world examples
     - - NASA cFE Functional Requirements
       - MISRA C coding guidelines,
       - NASA Software Engineering Requirements NPR 7150.2
     - - ECSS Software ECSS-E-ST-40C
[/FREETEXT]

[/SECTION]
