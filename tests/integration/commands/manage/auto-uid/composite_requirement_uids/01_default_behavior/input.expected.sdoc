[DOCUMENT]
TITLE: Hello world doc

[COMPOSITE_REQUIREMENT]
UID: REQ-1
STATEMENT: System shall do 1.

[REQUIREMENT]
UID: REQ-2
STATEMENT: System shall do 1.

[/COMPOSITE_REQUIREMENT]

[COMPOSITE_REQUIREMENT]
UID: REQ-3
STATEMENT: System shall do 2.

[REQUIREMENT]
UID: REQ-4
STATEMENT: System shall do 2.

[/COMPOSITE_REQUIREMENT]

[COMPOSITE_REQUIREMENT]
UID: REQ-5
STATEMENT: System shall do 3.

[REQUIREMENT]
UID: REQ-6
STATEMENT: System shall do 3.

[/COMPOSITE_REQUIREMENT]
