[DOCUMENT]
TITLE: Document 1

[FREETEXT]
Hello world!
[/FREETEXT]

[REQUIREMENT]
UID: REQ-1
STATEMENT: >>>
Requirement statement.
<<<

[REQUIREMENT]
UID: REQ-2
STATEMENT: >>>
Requirement statement.
<<<
