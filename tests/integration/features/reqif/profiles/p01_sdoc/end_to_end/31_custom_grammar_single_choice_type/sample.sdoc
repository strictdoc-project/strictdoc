[DOCUMENT]
TITLE: sample

[GRAMMAR]
ELEMENTS:
- TAG: REQUIREMENT
  FIELDS:
  - TITLE: CHOICE_FIELD
    TYPE: SingleChoice(A, B, C, D)
    REQUIRED: False
  - TITLE: CHOICE_FIELD_2
    TYPE: SingleChoice("A(B)", "B(C)", "C(D)")
    REQUIRED: False
  - TITLE: STATEMENT
    TYPE: String
    REQUIRED: False

[REQUIREMENT]
CHOICE_FIELD: A
CHOICE_FIELD_2: A(B)
