[DOCUMENT]
TITLE: Hello world doc

[SECTION]
TITLE: Referencing section

[TEXT]
STATEMENT: >>>
See the [LINK: AD1] for more details.

See the [LINK: AD2] for more details.

See the [LINK: Interface_Control_Document] for more details.
<<<

[TEXT]
STATEMENT: >>>
See the [LINK: AD4] for more details.

See the [LINK: AD5] for more details.

See the [LINK: Supplemental Guide] for more details.
<<<

[/SECTION]
