# Documentation export by StrictDoc

# Specification: Document 1

## R1: Abstract
Document 1 free text.

## R2: Document 1 section
Document 1 statement.

# Specification: Document 2

## R3: Abstract
Document 2 free text.

## R4: Document 2 section
Document 2 statement.
