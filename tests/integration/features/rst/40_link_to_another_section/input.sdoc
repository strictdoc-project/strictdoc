[DOCUMENT]
TITLE: Hello world doc

[[SECTION]]
UID: CHAPTER_1
TITLE: Chapter 1

[TEXT]
STATEMENT: >>>
Here's the chapter 1.
<<<

[[/SECTION]]

[[SECTION]]
TITLE: Chapter 2

[TEXT]
STATEMENT: >>>
See [LINK: CHAPTER_1] for more details.
<<<

[[/SECTION]]
