[DOCUMENT]
TITLE: Hello world doc

[REQUIREMENT]
UID: LOW-REQ-001
TITLE: Low-level requirement title #1
STATEMENT: Low-level requirement statement #1.
RELATIONS:
- TYPE: Parent
  VALUE: REQ-001

[REQUIREMENT]
UID: LOW-REQ-002
TITLE: Low-level requirement title #2
STATEMENT: Low-level requirement statement #2.
RELATIONS:
- TYPE: Parent
  VALUE: REQ-002

[REQUIREMENT]
UID: LOW-REQ-003
TITLE: Low-level requirement title #3
STATEMENT: Low-level requirement statement #3.
RELATIONS:
- TYPE: Parent
  VALUE: REQ-003
