[DOCUMENT]
TITLE: Hello world doc

[REQUIREMENT]
UID: REQ-1
TITLE: Requirement Title
STATEMENT: Requirement Statement

[REQUIREMENT]
UID: REQ-2
TITLE: Requirement Title
STATEMENT: Requirement Statement
RELATIONS:
- TYPE: File
  VALUE: file.py
  CLASS: Foo
