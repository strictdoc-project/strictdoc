[DOCUMENT]
TITLE: Hello world doc

[REQUIREMENT]
UID: REQ-1
TITLE: Requirement Title
STATEMENT: The body foo links to the declaration Foo.

[REQUIREMENT]
UID: REQ-2
TITLE: Requirement Title #2
STATEMENT: Requirement Statement #2
RELATIONS:
- TYPE: File
  VALUE: pkg.adb
  FUNCTION: pkg.hello_World
