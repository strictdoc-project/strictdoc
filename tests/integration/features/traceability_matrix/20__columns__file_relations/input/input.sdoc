[DOCUMENT]
TITLE: Hello world doc

[REQUIREMENT]
UID: REQ-001
TITLE: Requirement Title #1
STATEMENT: Requirement Statement #1
RELATIONS:
- TYPE: File
  VALUE: file1.py

[REQUIREMENT]
UID: REQ-002
TITLE: Requirement Title #2
STATEMENT: Requirement Statement #2
RELATIONS:
- TYPE: File
  VALUE: file2.py

[REQUIREMENT]
UID: REQ-003
TITLE: Requirement Title #3
STATEMENT: Requirement Statement #3
RELATIONS:
- TYPE: File
  VALUE: file3.py
