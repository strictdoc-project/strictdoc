[DOCUMENT]
TITLE: sample

[GRAMMAR]
ELEMENTS:
- TAG: SECTION
  PROPERTIES:
    IS_COMPOSITE: True
  FIELDS:
  - TITLE: UID
    TYPE: String
    REQUIRED: False
  - TITLE: LEVEL
    TYPE: String
    REQUIRED: False
  - TITLE: PREFIX
    TYPE: String
    REQUIRED: False
  - TITLE: TITLE
    TYPE: String
    REQUIRED: False
- TAG: REQUIREMENT
  FIELDS:
  - TITLE: UID
    TYPE: String
    REQUIRED: False
  - TITLE: LEVEL
    TYPE: String
    REQUIRED: False
  - TITLE: STATUS
    TYPE: String
    REQUIRED: False
  - TITLE: TAGS
    TYPE: String
    REQUIRED: False
  - TITLE: TITLE
    TYPE: String
    REQUIRED: False
  - TITLE: STATEMENT
    TYPE: String
    REQUIRED: False
  - TITLE: RATIONALE
    TYPE: String
    REQUIRED: False
  - TITLE: COMMENT
    TYPE: String
    REQUIRED: False

[[SECTION]]
TITLE: Section #1

[[SECTION]]
TITLE: Section #1.1

[REQUIREMENT]
UID: REQ-1.1.1
STATEMENT: >>>
The mapping function shall map requirement_ID to UID.
<<<

[REQUIREMENT]
UID: REQ-1.1.2
STATEMENT: >>>
The mapping function shall map requirement_ID to UID.
<<<

[[/SECTION]]

[[SECTION]]
TITLE: Section #1.2

[REQUIREMENT]
UID: REQ-1.2.1
STATEMENT: >>>
The mapping function shall map requirement_ID to UID.
<<<

[REQUIREMENT]
UID: REQ-1.2.2
STATEMENT: >>>
The mapping function shall map requirement_ID to UID.
<<<

[[/SECTION]]

[[/SECTION]]
