[DOCUMENT]
TITLE: Doc with a requirement that have no title

[REQUIREMENT]
UID: REQ1
TITLE: Requirement 1
STATEMENT: >>>
System shall do #1.
<<<
COMMENT: >>>
Requirement 1 comment #1.
<<<
COMMENT: >>>
Requirement 1 comment #2.
<<<

[SECTION]
TITLE: User interfaces

[FREETEXT]
Some free text...
[/FREETEXT]

[/SECTION]
