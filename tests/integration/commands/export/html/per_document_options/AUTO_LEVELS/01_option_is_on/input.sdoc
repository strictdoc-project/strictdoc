[DOCUMENT]
TITLE: Hello world doc
OPTIONS:
  AUTO_LEVELS: On

[SECTION]
TITLE: Section 1.2.3

[COMPOSITE_REQUIREMENT]
STATEMENT: Composite requirement 4.5.6

[REQUIREMENT]
STATEMENT: Requirement 7.8.9

[/COMPOSITE_REQUIREMENT]

[/SECTION]
