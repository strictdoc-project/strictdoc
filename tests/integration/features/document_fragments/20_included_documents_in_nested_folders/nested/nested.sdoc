[DOCUMENT]
TITLE: Hello world doc 2
OPTIONS:
  AUTO_LEVELS: On

[TEXT]
STATEMENT: >>>
.. image:: _assets/file.svg
   :alt: Test image
   :class: image
   :width: 100%
<<<

[DOCUMENT_FROM_FILE]
FILE: subnested/subnested.sdoc
