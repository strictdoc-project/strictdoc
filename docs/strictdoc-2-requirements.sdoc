[DOCUMENT]
TITLE: StrictDoc Requirements
OPTIONS:
  REQUIREMENT_STYLE: Inline

[SECTION]
TITLE: High-level requirements

[REQUIREMENT]
UID: SDOC-HIGH-REQS-MANAGEMENT
REFS:
- TYPE: Parent
  VALUE: GOAL-1-TOOL-SUPPORT
TITLE: Requirements management
STATEMENT: StrictDoc shall enable requirements management.

[REQUIREMENT]
UID: SDOC-HIGH-DATA-MODEL
TITLE: Data model
STATEMENT: StrictDoc shall be based on a well-defined data model.
COMMENT: >>>
StrictDoc is a result of several attempts to find a solution for working with
text-based requirements:

- StrictDoc, first generation: Markdown-based C++ program. Custom requirements
  metadata in YAML.
- StrictDoc, second generation: RST/Sphinx-based Python program. Using Sphinx
  extensions to manage meta information.

The result of these efforts was the realization that a text-based requirements
and specifications management tool could be built on top of a domain-specific
language (DSL) created specifically for the purpose of writing requirements and
specifications documents. Such a language allows an explicit definition of a
document data model which is called "grammar".
<<<

[REQUIREMENT]
TITLE: Command-line interface
STATEMENT: StrictDoc shall provide a command-line interface.

[COMPOSITE_REQUIREMENT]
TITLE: Platform support
STATEMENT: StrictDoc shall work on all major platforms.

[REQUIREMENT]
TITLE: macOS support
STATEMENT: StrictDoc shall work on macOS systems.

[REQUIREMENT]
TITLE: Linux support
STATEMENT: StrictDoc shall work on Linux systems.

[REQUIREMENT]
TITLE: Windows support
STATEMENT: StrictDoc shall work on Windows systems.

[/COMPOSITE_REQUIREMENT]

[REQUIREMENT]
UID: SDOC-HIGH-VALIDATION
TITLE: Requirements validation
STATEMENT: StrictDoc shall allow validation of requirement documents.

[REQUIREMENT]
TITLE: Requirements text format
STATEMENT: StrictDoc shall allow storage of requirements in a plain-text human readable form.

[REQUIREMENT]
TITLE: Linking requirements
STATEMENT: StrictDoc shall support linking requirements to each other.

[REQUIREMENT]
TITLE: Scalability
STATEMENT: StrictDoc shall allow working with large documents and document trees containing at least 10000 requirement items.

[REQUIREMENT]
UID: SDOC-HIGH-REQS-TRACEABILITY
TITLE: Traceability
STATEMENT: StrictDoc shall support traceability of requirements.

[REQUIREMENT]
TITLE: Visualization
STATEMENT: StrictDoc shall provide means for visualization of requirement documents.

[REQUIREMENT]
TITLE: Open source software
STATEMENT: StrictDoc shall always be free and open source software.

[/SECTION]

[SECTION]
TITLE: Implementation requirements

[REQUIREMENT]
UID: SDOC-IMPL-PARAL
TITLE: Parallelization
STATEMENT: StrictDoc shall enable parallelization of the time-consuming parts of the code.

[REQUIREMENT]
UID: SDOC-IMPL-INCREMENTAL
TITLE: Incremental generation
STATEMENT: StrictDoc shall enable incremental generation of the documents.
COMMENT: >>>
When exporting documentation tree, StrictDoc shall regenerate only changed
documents and files.
<<<

[/SECTION]

[SECTION]
TITLE: Data model

[REQUIREMENT]
UID: SDOC-DM-MODEL
REFS:
- TYPE: Parent
  VALUE: SDOC-HIGH-REQS-MANAGEMENT
- TYPE: Parent
  VALUE: SDOC-HIGH-DATA-MODEL
TITLE: Modeling capability
STATEMENT: StrictDoc's Data Model shall accommodate for maximum possible standard requirement document formats.
COMMENT: >>>
Examples of standard requirements documents include but are not limited to:

- Non-nested requirement lists split by categories
  (e.g., Functional Requirements, Interface Requirements, Performance Requirements, etc.)
<<<

[COMPOSITE_REQUIREMENT]
TITLE: Project
STATEMENT: >>>
StrictDoc shall support the "Project" concept as a top-level entity that serves
for grouping of SDoc documents into a single project documentation tree.
<<<

[REQUIREMENT]
TITLE: Project title
STATEMENT: >>>
Project shall have a "Title" property.
<<<
COMMENT: >>>
Currently, the project title aspect is not part of the SDoc grammar. It is
simply specified via the ``--project-title`` command-line option. This might
change when the project title will be configured as part of the project-level
config file (TOML or SDoc-like grammar).
<<<

[/COMPOSITE_REQUIREMENT]

[SECTION]
TITLE: Document

[FREETEXT]
TBD
[/FREETEXT]

[/SECTION]

[SECTION]
TITLE: Section

[FREETEXT]
TBD
[/FREETEXT]

[/SECTION]

[SECTION]
TITLE: Requirement item

[REQUIREMENT]
TITLE: Statement
STATEMENT: Requirement item shall have a statement.

[COMPOSITE_REQUIREMENT]
TITLE: UID identifier
STATEMENT: Requirement item may have an UID identifier.

[REQUIREMENT]
TITLE: UID identifier format
STATEMENT: StrictDoc shall not impose any restrictions on the UID field format.
COMMENT: >>>
Conventions used for requirement UIDs can be very different. And there seems to
be no way to define a single rule.

Some examples:

- FUN-003
- cES1008, cTBL6000.1 (NASA cFS)
- Requirements without a number, e.g. SDOC-HIGH-DATA-MODEL (StrictDoc)
- SAVOIR.OBC.PM.80 (SAVOIR)
<<<

[/COMPOSITE_REQUIREMENT]

[REQUIREMENT]
TITLE: Title
STATEMENT: Requirement item may have an title.

[REQUIREMENT]
TITLE: References
STATEMENT: Requirement item may have one or more references.

[REQUIREMENT]
TITLE: Comments
STATEMENT: Requirement item may have one or more comments.

[REQUIREMENT]
TITLE: Special fields
STATEMENT: StrictDoc shall support customization of the default Requirement's grammar with special fields.
COMMENT: >>>
Examples:

- RAIT compliance fields (Review of design, analysis, inspection, testing)
- Automotive Safety Integrity Level level (ASIL).
<<<

[/SECTION]

[SECTION]
TITLE: Composite Requirement item

[FREETEXT]
TBD
[/FREETEXT]

[/SECTION]

[COMPOSITE_REQUIREMENT]
TITLE: Links
STATEMENT: StrictDoc's data model shall support linking document content nodes to each other.

[REQUIREMENT]
TITLE: Parent links
STATEMENT: StrictDoc's data model shall support linking a requirement to another requirement using PARENT link.

[/COMPOSITE_REQUIREMENT]

[/SECTION]

[SECTION]
TITLE: SDoc file format

[REQUIREMENT]
UID: SDOC-FMT-PRIMARY
REFS:
- TYPE: Parent
  VALUE: SDOC-DM-MODEL
TITLE: Primary text implementation
STATEMENT: The SDoc format shall support encoding the Strict Doc Data Model in a plain-text human readable form.

[COMPOSITE_REQUIREMENT]
UID: SDOC-FMT-GRAMMAR
REFS:
- TYPE: Parent
  VALUE: SDOC-HIGH-DATA-MODEL
- TYPE: File
  VALUE: strictdoc/backend/sdoc/grammar/grammar.py
TITLE: Grammar
STATEMENT: The SDoc format shall be based on a fixed grammar.

[REQUIREMENT]
TITLE: No indentation
STATEMENT: The SDoc grammar's building blocks shall not allow any indentation.
COMMENT: >>>
Rationale: Adding indentation to any of the fields does not scale well when the
documents have deeply nested section structure as well as when the size of the
paragraphs becomes sufficiently large. Keeping every keyword like [REQUIREMENT]
or [COMMENT] with no indentation ensures that one does not have to think about
possible indentation issues.
<<<

[/COMPOSITE_REQUIREMENT]

[REQUIREMENT]
TITLE: Type safety
STATEMENT: The SDoc format shall allow type-safe encoding of requirement documents.

[/SECTION]

[SECTION]
TITLE: Export and import capabilities

[SECTION]
TITLE: General

[REQUIREMENT]
TITLE: Generated file names
STATEMENT: >>>
StrictDoc shall preserve original document file names when generating to all
export formats.
<<<

[/SECTION]

[SECTION]
TITLE: HTML Export

[REQUIREMENT]
TITLE: Single document: Normal form
STATEMENT: StrictDoc shall export single document pages in a normal document-like form.

[REQUIREMENT]
TITLE: Single document: Tabular form
STATEMENT: StrictDoc shall export single document pages in a tabular form.

[REQUIREMENT]
REFS:
- TYPE: Parent
  VALUE: SDOC-HIGH-REQS-TRACEABILITY
TITLE: Single document: 1-level traceability
STATEMENT: StrictDoc shall export 1-level traceability document.

[REQUIREMENT]
REFS:
- TYPE: Parent
  VALUE: SDOC-HIGH-REQS-TRACEABILITY
TITLE: Single document: Deep traceability
STATEMENT: StrictDoc shall export deep traceability document.

[REQUIREMENT]
TITLE: Left panel: Table of contents
STATEMENT: StrictDoc shall export all HTML pages with Table of Contents.

[/SECTION]

[SECTION]
TITLE: PDF Export

[REQUIREMENT]
TITLE: Sphinx documentation generator
STATEMENT: StrictDoc shall support exporting documents to Sphinx/RST format.

[/SECTION]

[REQUIREMENT]
UID: SDOC-GEN-EXCEL-EXPORT
REFS:
- TYPE: File
  VALUE: strictdoc/backend/excel/export/excel_generator.py
TITLE: Excel Export
STATEMENT: StrictDoc shall support exporting documents to Excel format.

[REQUIREMENT]
TITLE: ReqIF import/export
STATEMENT: StrictDoc shall support the ReqIF format.

[/SECTION]

[SECTION]
TITLE: Validation

[REQUIREMENT]
UID: SDOC-VALIDATION-UNIQUE-UID
REFS:
- TYPE: Parent
  VALUE: SDOC-HIGH-VALIDATION
TITLE: Uniqueness of UID identifiers in a document tree
STATEMENT: StrictDoc shall ensure that each UID used in a document tree is unique.
COMMENT: This is implemented but the error message shall be made more readable.

[REQUIREMENT]
UID: SDOC-VALIDATION-NO-CYCLES
REFS:
- TYPE: Parent
  VALUE: SDOC-HIGH-VALIDATION
- TYPE: File
  VALUE: strictdoc/core/tree_cycle_detector.py
- TYPE: File
  VALUE: strictdoc/core/traceability_index_builder.py
TITLE: No cycles in a document tree
STATEMENT: >>>
StrictDoc shall ensure that no requirements in document tree reference each other.
<<<

[REQUIREMENT]
UID: SDOC-VALIDATION-VALID-HTML
REFS:
- TYPE: Parent
  VALUE: SDOC-HIGH-VALIDATION
TITLE: Valid HTML markup
STATEMENT: StrictDoc's HTML export tests shall validate the generated HTML markup.
COMMENT: First candidate: Table of contents and its nested ``<ul>/<li>`` items.

[/SECTION]

[SECTION]
TITLE: Traceability and coverage

[COMPOSITE_REQUIREMENT]
TITLE: Linking with implementation artifacts
STATEMENT: StrictDoc shall support linking requirements to files.

[REQUIREMENT]
TITLE: Validation: Broken links from requirements to source files
STATEMENT: >>>
StrictDoc shall warn a user about all requirements whose links reference source
files that do not exist.
<<<

[REQUIREMENT]
TITLE: Validation: Broken links from source files to requirements
STATEMENT: >>>
StrictDoc shall warn a user about all source files whose links reference
requirements that do not exist.
<<<

[/COMPOSITE_REQUIREMENT]

[REQUIREMENT]
TITLE: Requirements coverage
STATEMENT: StrictDoc shall generate requirements coverage information.
COMMENT: >>>
Requirements coverage screen shows how requirements are linked with source files.
<<<

[REQUIREMENT]
TITLE: Source coverage
STATEMENT: StrictDoc shall generate source coverage information.
COMMENT: >>>
Source coverage screen shows how source files are linked with requirements.
<<<

[/SECTION]

[SECTION]
TITLE: Design decisions

[SECTION]
TITLE: Building blocks

[REQUIREMENT]
TITLE: TextX
STATEMENT: TextX shall be used for StrictDoc grammar definition and parsing of the sdoc files.
COMMENT: >>>
TextX is an easy-to-install Python tool. It is fast, works out of the box.
<<<

[REQUIREMENT]
TITLE: Jinja2
STATEMENT: Jinja2 shall be used for rendering HTML templates.

[REQUIREMENT]
TITLE: Sphinx and Docutils
STATEMENT: >>>
Sphinx and Docutils shall be used for the following capabilities:

- Support of Restructured Text (reST) format
- Generation of RST documents into HTML
- Generation of RST documents into PDF using LaTeX
- Generating documentation websites using Sphinx
<<<

[/SECTION]

[/SECTION]
