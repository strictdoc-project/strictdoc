[DOCUMENT]
TITLE: Design Document
OPTIONS:
  REQUIREMENT_STYLE: Table
  REQUIREMENT_IN_TOC: True

[SECTION]
TITLE: Design decisions

[SECTION]
TITLE: Building blocks

[REQUIREMENT]
TITLE: TextX
STATEMENT: TextX shall be used for StrictDoc grammar definition and parsing of the sdoc files.
COMMENT: >>>
TextX is an easy-to-install Python tool. It is fast, works out of the box.
<<<

[REQUIREMENT]
TITLE: Jinja2
STATEMENT: Jinja2 shall be used for rendering HTML templates.

[REQUIREMENT]
TITLE: Sphinx and Docutils
STATEMENT: >>>
Sphinx and Docutils shall be used for the following capabilities:

- Support of Restructured Text (reST) format
- Generation of RST documents into HTML
- Generation of RST documents into PDF using LaTeX
- Generating documentation websites using Sphinx
<<<

[/SECTION]

[/SECTION]
