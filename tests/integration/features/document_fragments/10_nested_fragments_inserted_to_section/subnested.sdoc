[DOCUMENT]
TITLE: Hello world doc 3
OPTIONS:
  AUTO_LEVELS: On

[SECTION]
TITLE: Section 1.2.3

[COMPOSITE_REQUIREMENT]
TITLE: Composite requirement 4.5.6
STATEMENT: ...

[REQUIREMENT]
TITLE: Requirement 7.8.9
STATEMENT: ...

[/COMPOSITE_REQUIREMENT]

[/SECTION]
