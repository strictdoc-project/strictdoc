[DOCUMENT]
TITLE: StrictDoc/Sandbox

[FREETEXT]
This is a sandbox file for experiments.

$$
\\mathbf{\\underline{k}}_{\\text{a}} =
\\mathbf{\\underline{i}}_{\\text{a}} \\times
\\mathbf{\\underline{j}}_{\\text{a}}
$$
[/FREETEXT]

[SECTION]
TITLE: Section 1

[REQUIREMENT]
UID: REQ-001
TAGS: Foo, Bar, Baz
SPECIAL_FIELDS:
  OWNER: Some Owner
  PRIORITY: High
TITLE: Requirement #1 title
STATEMENT: >>>
Requirement #1 statement

.. image:: _assets/sandbox1.svg
   :alt: Sandbox demo
   :class: image

.. image:: _assets/sandbox1.png
   :alt: Sandbox demo
   :class: image
<<<
BODY: >>>
The Jung personality test measures your preferences for dealing with and relating to people, processing information, making decisions and organizing your life. Its results give you a good overview of your personality and behavior. You can then see how your Jung types match up with a potential employer's requirements.
<<<
COMMENT: >>>
Requirement #1 multiline comment
<<<

[REQUIREMENT]
TITLE: Table example
STATEMENT: >>>
.. list-table:: Table Example
   :widths: 25 25 50
   :header-rows: 1

   * - Heading row 1, column 1
     - Heading row 1, column 2
     - Heading row 1, column 3
   * - Row 1, column 1
     -
     - Row 1, column 3
   * - Row 2, column 1
     - Row 2, column 2
     - Row 2, column 3
<<<

[/SECTION]

[SECTION]
TITLE: Section 2

[REQUIREMENT]
UID: REQ-002
STATUS: Draft
TAGS: Foo, Bar, Baz
REFS:
- TYPE: Parent
  VALUE: REQ-001
TITLE: Requirement #2 title
STATEMENT: Requirement #2 statement
COMMENT: >>>
Requirement #2 multiline comment
<<<

[COMPOSITE_REQUIREMENT]
UID: REQ-003
STATUS: Draft
TAGS: Foo, Bar, Baz
TITLE: Composite Requirement #3 title
STATEMENT: Composite Requirement #3 statement
COMMENT: >>>
Composite Requirement #3 multiline comment
<<<

[REQUIREMENT]
UID: REQ-003-1
STATUS: Draft
TAGS: Foo, Bar, Baz
TITLE: Requirement #3.1 title
STATEMENT: Requirement #3.1 statement
COMMENT: >>>
Requirement #3.1 multiline comment
<<<

[REQUIREMENT]
UID: REQ-003-2
STATUS: Draft
TAGS: Foo, Bar, Baz
TITLE: Requirement #3.2 title
STATEMENT: Requirement #3.2 statement
COMMENT: >>>
Requirement #3.2 multiline comment
<<<

[/COMPOSITE_REQUIREMENT]

[/SECTION]

[SECTION]
TITLE: File References (Early experimental feature, do not use yet)

[REQUIREMENT]
UID: REQ-FILE-REF
REFS:
- TYPE: File
  VALUE: developer/sandbox/hello_world.py
TITLE: Simple file reference link
STATEMENT: Requirement statement

[REQUIREMENT]
UID: REQ-FILE-REF2
REFS:
- TYPE: File
  VALUE: developer/sandbox/hello_world.py
TITLE: Simple file reference link
STATEMENT: Requirement statement

[REQUIREMENT]
UID: REQ-FILE-REF3
REFS:
- TYPE: File
  VALUE: developer/sandbox/hello_world.py
TITLE: Simple file reference link
STATEMENT: Requirement statement

[REQUIREMENT]
UID: REQ-FILE-REF4
REFS:
- TYPE: File
  VALUE: developer/sandbox/hello_world.py
TITLE: Simple file reference link
STATEMENT: Requirement statement

[REQUIREMENT]
UID: REQ-FILE-REF5
REFS:
- TYPE: File
  VALUE: developer/sandbox/hello_world.py
TITLE: Simple file reference link
STATEMENT: Requirement statement

[REQUIREMENT]
UID: REQ-FILE-REF6
REFS:
- TYPE: File
  VALUE: developer/sandbox/hello_world.py
TITLE: Simple file reference link
STATEMENT: Requirement statement

[REQUIREMENT]
UID: REQ-FILE-REF7
REFS:
- TYPE: File
  VALUE: developer/sandbox/hello_world.py
TITLE: Simple file reference link
STATEMENT: Requirement statement

[REQUIREMENT]
UID: REQ-FILE-REF8
REFS:
- TYPE: File
  VALUE: developer/sandbox/hello_world.py
- TYPE: File
  VALUE: developer/sandbox/nested_folder/hello_world_2.py
TITLE: Simple file reference link
STATEMENT: Requirement statement

[REQUIREMENT]
UID: REQ-FILE-REF-NESTED-FOLDER
REFS:
- TYPE: File
  VALUE: developer/sandbox/nested_folder/hello_world_2.py
TITLE: Simple file reference link (nested folder)
STATEMENT: Requirement statement

[REQUIREMENT]
UID: REQ-FILE-SUM
REFS:
- TYPE: File
  VALUE: developer/sandbox/hello_world.py
TITLE: Adding two numbers
STATEMENT: Python3 program shall add two numbers

[REQUIREMENT]
UID: REQ-FILE-C
REFS:
- TYPE: File
  VALUE: developer/sandbox/hello_world.c
TITLE: C Hello world program
STATEMENT: Hello world program shall print "Hello World!".

[REQUIREMENT]
UID: REQ-FILE-CPP
REFS:
- TYPE: File
  VALUE: developer/sandbox/hello_world.cpp
TITLE: C++ Hello world program
STATEMENT: Hello world program shall print "Hello World!".

[REQUIREMENT]
UID: REQ-FILE-CPP-2
REFS:
- TYPE: File
  VALUE: developer/sandbox/hello_world.cpp
TITLE: C++ Hello world program
STATEMENT: Hello world program shall print "Hello World!".

[/SECTION]
