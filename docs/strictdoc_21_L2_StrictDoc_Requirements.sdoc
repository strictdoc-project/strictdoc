[DOCUMENT]
MID: 8a87daf19a7c487f89f396406a974509
TITLE: StrictDoc Requirements Specification (L2)
VERSION: Git commit: @GIT_VERSION, Git branch: @GIT_BRANCH
DATE: @GIT_COMMIT_DATETIME
PREFIX: SDOC-SRS-
OPTIONS:
  ENABLE_MID: True

[GRAMMAR]
ELEMENTS:
- TAG: SECTION
  PROPERTIES:
    IS_COMPOSITE: True
    VIEW_STYLE: Narrative
  FIELDS:
  - TITLE: MID
    TYPE: String
    REQUIRED: False
  - TITLE: UID
    TYPE: String
    REQUIRED: False
  - TITLE: TITLE
    TYPE: String
    REQUIRED: True
- TAG: TEXT
  FIELDS:
  - TITLE: MID
    TYPE: String
    REQUIRED: True
  - TITLE: UID
    TYPE: String
    REQUIRED: False
  - TITLE: STATEMENT
    TYPE: String
    REQUIRED: False
- TAG: REQUIREMENT
  PROPERTIES:
    VIEW_STYLE: Table
  FIELDS:
  - TITLE: MID
    TYPE: String
    REQUIRED: False
  - TITLE: UID
    TYPE: String
    REQUIRED: False
  - TITLE: STATUS
    TYPE: String
    REQUIRED: False
  - TITLE: TITLE
    TYPE: String
    REQUIRED: False
  - TITLE: STATEMENT
    TYPE: String
    REQUIRED: False
  - TITLE: RATIONALE
    TYPE: String
    REQUIRED: False
  - TITLE: COMMENT
    TYPE: String
    REQUIRED: False
  RELATIONS:
  - TYPE: Parent
  - TYPE: File

[[SECTION]]
MID: bd8a7931c1e04df9bf08d291488c67aa
TITLE: SDoc data model

[REQUIREMENT]
MID: e8d5b55055254144b96d1ffeb587ec72
UID: SDOC-SRS-18
STATUS: Active
TITLE: Data model
STATEMENT: >>>
StrictDoc shall be based on a data model.
<<<
RATIONALE: >>>
Designing StrictDoc with a goal of having a consistent data model ensures that the tool:

1) can support a rich set of use cases,
2) model the existing documentation templates used by the industries,
3) interface well with other formats for storing documentation and requirements, e.g., ReqIF and SPDX.
<<<
COMMENT: >>>
Verification: data model diagram TBD.
<<<
RELATIONS:
- TYPE: Parent
  VALUE: SDOC-SSS-88
- TYPE: Parent
  VALUE: SDOC-SSS-58

[REQUIREMENT]
MID: 3b31cad22529476db01aca41caf39750
UID: SDOC-SRS-26
STATUS: Active
TITLE: Requirement model
STATEMENT: >>>
StrictDoc's data model shall support modeling requirements.
<<<
RELATIONS:
- TYPE: Parent
  VALUE: SDOC-SSS-4

[REQUIREMENT]
MID: 8e2ffffd33af4a969d5bb7ca40cb49a4
UID: SDOC-SRS-100
STATUS: Active
TITLE: Requirement model fields
STATEMENT: >>>
StrictDoc's "Requirement" model shall support configurable fields system.
<<<
RELATIONS:
- TYPE: Parent
  VALUE: SDOC-SSS-62

[REQUIREMENT]
MID: 2d4020ba06d74571aef7aafe8604215b
UID: SDOC-SRS-132
STATUS: Active
TITLE: Requirement model default fields
STATEMENT: >>>
By default, the Requirement shall support the following fields:

- MID
- UID
- STATUS
- TITLE
- STATEMENT
- RATIONALE
- COMMENT.
<<<
RATIONALE: >>>
These fields are the most typical fields found in requirement documents.
<<<
RELATIONS:
- TYPE: Parent
  VALUE: SDOC-SSS-61

[REQUIREMENT]
MID: f94419a390f2403daa3c4cd0e96f6cb6
UID: SDOC-SRS-98
STATUS: Active
TITLE: Document model
STATEMENT: >>>
StrictDoc's data model shall support modeling documents.
<<<
RELATIONS:
- TYPE: Parent
  VALUE: SDOC-SSS-64

[REQUIREMENT]
MID: 435f856197d743c1b9b1dcbe91a22863
UID: SDOC-SRS-110
STATUS: Active
TITLE: Document metadata
STATEMENT: >>>
StrictDoc's data model shall support a Document metadata model including at least:

- UID
- Document version
- Document classification
- Document authors.
<<<
RELATIONS:
- TYPE: Parent
  VALUE: SDOC-SSS-53
- TYPE: Parent
  VALUE: SDOC-SSS-75

[REQUIREMENT]
MID: abcced8724d743c1b9b1dcbe91a22863
UID: SDOC-SRS-151
STATUS: Active
TITLE: Document configuration
STATEMENT: >>>
StrictDoc's data model shall support configuring the document options:

- Enable/disable MID
- Markup choice, e.g., RST, HTML, etc.
- Levels (automatic or manual)
- Node style
- Default presentation view.
<<<
RELATIONS:
- TYPE: Parent
  VALUE: SDOC-SSS-53
- TYPE: Parent
  VALUE: SDOC-SSS-75

[REQUIREMENT]
MID: 63821c507d584cf985f05904710b9779
UID: SDOC-SRS-99
STATUS: Active
TITLE: Section model
STATEMENT: >>>
StrictDoc's data model shall support a concept of a "Section" which nests other Sections, Requirements, Texts.
<<<
RATIONALE: >>>
"Section" corresponds to a chapter or a section in a document and helps to organize a document by grouping text nodes, requirements and other sections.
<<<
RELATIONS:
- TYPE: Parent
  VALUE: SDOC-SSS-51

[REQUIREMENT]
MID: 899d2f68749b4be1a3124fe4d01de1aa
UID: SDOC-SRS-135
STATUS: Active
TITLE: Free text
STATEMENT: >>>
StrictDoc's data model shall support a "Free Text" model, representing non-normative documentation content.
<<<
RATIONALE: >>>
Documentation comprises normative components, such as uniquely identifiable elements like requirements or design items, and non-normative components, including introductory text, overview chapters, and other content. The non-normative parts help provide a general understanding for the reader but do not contribute to traceability information. StrictDoc's free text is designed to store this type of non-normative information in SDoc documents.
<<<
RELATIONS:
- TYPE: Parent
  VALUE: SDOC-SSS-3

[REQUIREMENT]
MID: 983653fc26214f46977dc792d65ae65f
UID: SDOC-SRS-109
STATUS: Active
TITLE: Composeable document
STATEMENT: >>>
StrictDoc's data model shall allow composing a Document from other Documents.
<<<
RATIONALE: >>>
The logic behind the parent requirement remains fully relevant. Additionally, an alternative approach could involve using a dedicated entity, like "Fragment", to allow a Document to be composed of includable sections or document fragments. Managing composition at the Document level eliminates the need in additional entities like "Fragment", streamlining both the conceptual understanding and the practical implementation of composability.
<<<
COMMENT: >>>
The corresponding UI capability for Fragments CRUD is TBD.
<<<
RELATIONS:
- TYPE: Parent
  VALUE: SDOC-SSS-52
- TYPE: Parent
  VALUE: DO178-4

[REQUIREMENT]
MID: fad4cf5dcf4d40518c7c9826fd6bd18a
UID: SDOC-SRS-31
STATUS: Active
TITLE: Requirement relations
STATEMENT: >>>
The StrictDoc data model shall support connecting requirements using Parent and Child relations.
<<<
RATIONALE: >>>
Support of both Parent and Child relations allows to build typical requirements relations such as child-to-parent and less common relations when one document can have parent links to a parent document and child links to a child document (e.g., the so-called "compliance" or "tailoring matrix" documents may use this structure).
<<<
RELATIONS:
- TYPE: Parent
  VALUE: SDOC-SSS-7
- TYPE: Parent
  VALUE: SDOC-SSS-48

[REQUIREMENT]
MID: 9930894b08c44f5eba996c0a255e9e3f
UID: SDOC-SRS-101
STATUS: Active
TITLE: Requirement relation roles
STATEMENT: >>>
Each SDoc relation shall be optionally configurable with a relation role.

NOTE: A relation role is a string value. Typical examples: "refines", "verifies", "implements".
<<<
RELATIONS:
- TYPE: Parent
  VALUE: SDOC-SSS-8

[REQUIREMENT]
MID: fa090bc6976c4275aadbf522da6b920b
UID: SDOC-SRS-149
STATUS: Active
TITLE: Inline links
STATEMENT: >>>
StrictDoc shall support referencing any node by embedding a hyperlink within the text content of another node.
<<<
RATIONALE: >>>
The inline links do not replace the relations between SDoc nodes. Instead, an inline link could be an easy way to refer from one textual node to a chapter or a document. A common use case is "See section ABC for more details".
<<<

[REQUIREMENT]
MID: 54132bc6976c4275aadbf522da6b920b
UID: SDOC-SRS-150
STATUS: Active
TITLE: Inline anchors
STATEMENT: >>>
StrictDoc shall support adding anchors within the text content of any node, such that these anchors can be referenced by inline links from other nodes.
<<<
RATIONALE: >>>
Anchors allow authors to define precise reference points within SDoc node fields.
<<<

[[/SECTION]]

[[SECTION]]
MID: cbc7f72c6e0b4c858817bf17357105a5
TITLE: SDoc text markup

[REQUIREMENT]
MID: 27a6da48c65445539e536ee034921fb5
UID: SDOC-SRS-20
STATUS: Active
TITLE: SDoc markup language
STATEMENT: >>>
StrictDoc shall implement its own text markup language called S-Doc (strict-doc).
<<<
RATIONALE: >>>
The most commonly used Markdown format lacks the ability to store requirements metadata. While the RST syntax does allow for customization with directives to implement metadata extensions, its visual appearance contradicts other requirements of StrictDoc, such as the type-safety of the grammar and visual readability. Therefore, a markup language tailored specifically to the needs of the requirements tool provides direct control over the capabilities implemented in both the markup and the user interface.
<<<
RELATIONS:
- TYPE: Parent
  VALUE: SDOC-SSS-88
- TYPE: File
  VALUE: strictdoc/backend/sdoc/grammar/grammar.py
- TYPE: File
  VALUE: strictdoc/backend/sdoc/grammar/grammar_builder.py
- TYPE: File
  VALUE: strictdoc/backend/sdoc/reader.py
- TYPE: File
  VALUE: strictdoc/backend/sdoc/writer.py
- TYPE: File
  VALUE: strictdoc/backend/sdoc/processor.py

[REQUIREMENT]
MID: 1f147feed60245378de2e099facd196d
UID: SDOC-SRS-136
STATUS: Active
TITLE: Identical SDoc content by import/export roundtrip
STATEMENT: >>>
StrictDoc shall ensure that identical SDoc content is produced every time StrictDoc reads an SDoc file and then writes it to another SDoc file.
<<<
RATIONALE: >>>
A consistent import/export roundtrip implementation and testing reduces the risk of the SDoc bi-directional import/export corruption.
<<<
RELATIONS:
- TYPE: File
  FORMAT: Sourcecode
  VALUE: strictdoc/core/actions/export_action.py
- TYPE: File
  FORMAT: Sourcecode
  VALUE: tests/unit/strictdoc/backend/sdoc/test_dsl_passthrough.py
- TYPE: File
  FORMAT: Sourcecode
  VALUE: tests/unit/strictdoc/backend/sdoc/test_dsl_passthrough_document_views.py
- TYPE: File
  FORMAT: Sourcecode
  VALUE: tests/unit/strictdoc/backend/sdoc/test_dsl_passthrough_grammar.py
- TYPE: File
  FORMAT: Sourcecode
  VALUE: tests/unit/strictdoc/backend/sdoc/test_dsl_passthrough_relations.py
- TYPE: Parent
  VALUE: SDOC-SSS-94

[REQUIREMENT]
MID: f48a57c0cd764951a667127ce92fdb12
UID: SDOC-SRS-127
STATUS: Active
TITLE: SDoc and Git storage
STATEMENT: >>>
StrictDoc shall assume and implement capabilities for storage of SDoc files using Git version control system.
<<<
RELATIONS:
- TYPE: Parent
  VALUE: SDOC-SSS-87
- TYPE: Parent
  VALUE: SDOC-SSS-33
- TYPE: Parent
  VALUE: SDOC-SSS-84
- TYPE: Parent
  VALUE: SDOC-SSS-94

[REQUIREMENT]
MID: 9df34a7ab79842d99ee68303f334d4eb
UID: SDOC-SRS-104
STATUS: Active
TITLE: SDoc file extension
STATEMENT: >>>
The SDoc markup content shall be stored in files with .sdoc extension.
<<<
RATIONALE: >>>
Given that the name of the model is S-Doc (strict-doc), it is reasonable to make the document files have the ``.sdoc`` extension. This helps to identify the document files.
<<<
RELATIONS:
- TYPE: Parent
  VALUE: SDOC-SSS-80

[REQUIREMENT]
MID: 8dd6dd3979484dadbe71ac91aab50608
UID: SDOC-SRS-105
STATUS: Active
TITLE: One document per one SDoc file
STATEMENT: >>>
StrictDoc's SDoc file shall represent content of a single document.
<<<
COMMENT: >>>
A "Document" corresponds to a "Document" of the SDoc data model.
<<<
RELATIONS:
- TYPE: Parent
  VALUE: SDOC-SSS-64
- TYPE: Parent
  VALUE: DO178-1

[REQUIREMENT]
MID: e5e3033c13f24fa083423230da7994f7
UID: SDOC-SRS-19
STATUS: Active
TITLE: Fixed grammar
STATEMENT: >>>
StrictDoc's markup language shall be based on a well-defined grammar.
<<<
RELATIONS:
- TYPE: Parent
  VALUE: DO178-2
- TYPE: Parent
  VALUE: SDOC-SSS-55
- TYPE: Parent
  VALUE: SDOC-SSS-54
- TYPE: Parent
  VALUE: SDOC-SSS-94

[REQUIREMENT]
MID: b97418ceccff438cb0457ed4bdf1be47
UID: SDOC-SRS-93
STATUS: Active
TITLE: Default grammar fields
STATEMENT: >>>
The StrictDoc grammar shall have at least the following fields activated by default:

- UID
- STATUS
- TITLE
- STATEMENT
- RATIONALE
- COMMENT
- RELATIONS (references to other requirements)
<<<
RELATIONS:
- TYPE: Parent
  VALUE: SDOC-SSS-61

[REQUIREMENT]
MID: 8924c29136944f65ac5efc8b6b90a07b
UID: SDOC-SRS-21
STATUS: Active
TITLE: Custom grammar / fields
STATEMENT: >>>
The SDoc markup shall support custom grammars.
<<<
RATIONALE: >>>
A custom grammar allows a user to define their own configuration of requirement fields.
<<<
RELATIONS:
- TYPE: Parent
  VALUE: SDOC-SSS-62

[REQUIREMENT]
MID: 10d23bfbf4504c2e8c995ae89c500be4
UID: SDOC-SRS-122
STATUS: Active
TITLE: Importable grammars
STATEMENT: >>>
StrictDoc shall support an inclusion of a grammar stored in a separate file.
<<<
RATIONALE: >>>
A single grammar defined for several documents helps to standardize the structure of all documents in a documentation tree and removes the effort needed to create identical grammars all the time.
<<<
RELATIONS:
- TYPE: Parent
  VALUE: DO178-9
- TYPE: Parent
  VALUE: SDOC-SSS-52
- TYPE: File
  VALUE: strictdoc/backend/sdoc/grammar_reader.py
- TYPE: File
  VALUE: strictdoc/backend/sdoc/grammar/grammar_grammar.py

[REQUIREMENT]
MID: 5405c74a9eba4e9193007f01ea98bc85
UID: SDOC-SRS-22
STATUS: Active
TITLE: UID identifier format
STATEMENT: >>>
The SDoc markup shall only accept UID identifiers that consist of alphanumeric characters separated by a limited set of ("_", "-", ".") characters (TBD).
<<<
RATIONALE: >>>
A standardized UID format supports easier unique identification of requirements. It is easier to visually identify UIDs that look similar and common to a given industry.
<<<
COMMENT: >>>
This requirement may need a revision to accommodate for more UID formats.
<<<
RELATIONS:
- TYPE: Parent
  VALUE: SDOC-SSS-89

[REQUIREMENT]
MID: f871dfc381354daf820cc1e2b94fdb05
UID: SDOC-SRS-24
STATUS: Active
TITLE: Format-specific markup-to-HTML fragment writers
STATEMENT: >>>
StrictDoc shall render supported markup formats (at least RST and Markdown) to HTML fragments via dedicated format-specific writers selected by markup type.
<<<
RELATIONS:
- TYPE: Parent
  VALUE: SDOC-SSS-63
- TYPE: File
  FORMAT: Sourcecode
  VALUE: strictdoc/export/rst/rst_to_html_fragment_writer.py

[REQUIREMENT]
MID: b1b4f03d4e404a14be481626803fcfc2
UID: SDOC-SRS-27
STATUS: Active
TITLE: MathJAX
STATEMENT: >>>
StrictDoc's markup language shall support integration with MathJax.
<<<
RELATIONS:
- TYPE: Parent
  VALUE: SDOC-SSS-63
- TYPE: File
  VALUE: strictdoc/export/html/_static_extra/mathjax/tex-mml-chtml.js

[REQUIREMENT]
MID: 39f117b79cfa4a8485c458280b3d36ce
UID: SDOC-SRS-23
STATUS: Active
TITLE: No indentation
STATEMENT: >>>
SDoc text markup blocks shall all start from column 1, i.e., the nesting of the blocks is not allowed.
<<<
RATIONALE: >>>
Nesting large text blocks of free text and requirements compromises readability.
<<<
RELATIONS:
- TYPE: Parent
  VALUE: SDOC-SSS-55

[REQUIREMENT]
MID: 98628e1db3ca4f52b7632674b69dd657
UID: SDOC-SRS-25
STATUS: Active
TITLE: Type-safe fields
STATEMENT: >>>
SDoc markup shall provide "type safety" for all fields.

NOTE: "Type safety" means that each field has a type and a corresponding set of validation checks.
<<<
RELATIONS:
- TYPE: Parent
  VALUE: SDOC-SSS-55
- TYPE: File
  FORMAT: Sourcecode
  VALUE: strictdoc/backend/sdoc/grammar/type_system.py
- TYPE: Parent
  VALUE: SDOC-SSS-94

[[/SECTION]]

[[SECTION]]
MID: 408105d13e234f8aa73d017404eb5349
TITLE: Markdown text markup

[REQUIREMENT]
MID: 34246811634c493dbc771ae4c8bc3b14
UID: SDOC-SRS-183
STATUS: Active
TITLE: Read Markdown markup
STATEMENT: >>>
StrictDoc shall support reading Markdown files into in-memory SDoc documents.
<<<

[REQUIREMENT]
MID: 476d094833ac4b02af1d72ad27710b36
UID: SDOC-SRS-197
STATUS: Active
TITLE: Write Markdown markup
STATEMENT: >>>
StrictDoc shall support writing in-memory SDoc documents to Markdown files.
<<<

[REQUIREMENT]
MID: bc3b1411634c493dbc771ae4c8bc3b14
UID: SDOC-SRS-192
STATUS: Active
TITLE: Markdown files discovery
STATEMENT: >>>
StrictDoc shall discover Markdown files ``*.md`` and ``*.markdown`` using the same mechanism as used for SDoc files.
<<<

[REQUIREMENT]
MID: 245378eed60245378de2e099facd196d
UID: SDOC-SRS-196
STATUS: Active
TITLE: Identical Markdown content by import/export roundtrip
STATEMENT: >>>
StrictDoc shall ensure that identical Markdown content is produced every time StrictDoc reads a Markdown file and then writes it to another Markdown file.

The following aspects shall additionally apply:

- For MVP, line-endings should support both LF (Linux/macOS-style) and CRLF (Windows-style).
- The ``export --formats=markdown`` shall work for any format readable by StrictDoc, including Markdown itself, SDoc, RDF (future growth), ReqIF, etc.

NOTE: The write-back to Markdown file must happen through proper AST serialization, not just by giving back the original read Markdown source.

Exceptions:

Edge cases related to handling non-default input formats are postponed after the Markdown MVP is implemented. For example:

- Markdown reader encounters content format #3 (implicit field) via [LINK: SDOC-SRS-185], but writer always emits #1/#2 for content via [LINK: SDOC-SRS-198]. In this case the content will not be identical, but it is accepted for an MVP implementation.
<<<
RATIONALE: >>>
A consistent import/export roundtrip implementation and testing reduces the risk of the Markdown bi-directional import/export corruption.
<<<
RELATIONS:
- TYPE: Parent
  VALUE: SDOC-SSS-94

[REQUIREMENT]
MID: 11634c11634c493dbc771ae4c8bc3b14
UID: SDOC-SRS-191
STATUS: Active
TITLE: Markdown formats
STATEMENT: >>>
StrictDoc shall rely only on CommonMark core syntax v0.31.2 for SDoc node recognition.
<<<
RATIONALE: >>>
CommonMark core is the most portable target across parsers.
<<<

[REQUIREMENT]
MID: 41351111634c493dbc771ae4c8bc3b14
UID: SDOC-SRS-186
STATUS: Active
TITLE: Meta fields vs content fields
STATEMENT: >>>
StrictDoc shall recognize the following Markdown nodes as SDoc nodes:

.. code-block:: markdown

    ### Node title
    (empty line)
    **Meta field name 1**:
    **Meta field name 2**:
    ...
    (empty line)
    **Note content field 1**: ...
    (empty line)
    **Note content field 2**: ...
    ...

An SDoc node terminates when another Markdown section header or an EOF is encountered.

NOTE: There are no limitations to node level. A Markdown node can be at level 2, 3, etc. The level 1 is served for a root document node (document title with optional fields).
<<<

[REQUIREMENT]
MID: 54321111634c493dbc771ae4c8bc3b14
UID: SDOC-SRS-189
STATUS: Active
TITLE: One Markdown file — One SDoc document
STATEMENT: >>>
StrictDoc shall parse Markdown files using the "one Markdown file — one SDoc document" principle.
<<<

[REQUIREMENT]
MID: 12111111634c493dbc771ae4c8bc3b14
UID: SDOC-SRS-195
STATUS: Active
TITLE: Strict ban for redundant empty lines
STATEMENT: >>>
When a parsing Markdown file, if StrictDoc encounters two or more consecutive empty lines and the lines are not within a Markdown code block or a Markdown blockquote block, StrictDoc shall raise a StrictDocSemanticError.

NOTE: Empty lines includes whitespace-only lines which StrictDoc shall ban as well.
<<<

[REQUIREMENT]
MID: 999f59ede0f2477181bfc7667684df59
UID: SDOC-SRS-194
STATUS: Active
TITLE: Syntax for meta and content field names
STATEMENT: >>>
StrictDoc shall recognize the meta and content field names according to the following rules:

- Format is: ``**Field name**:``.
- Alphanumeric character range, separated by spaces, underscores or dashes.

Examples:

- ``**Statement**:``
- ``**STATEMENT**:``
- ``**IMPORTANT_STATEMENT**:``
- ``**SPDX-Req-ID**:``
<<<

[REQUIREMENT]
MID: 69f077ede0f2477181bfc7667684df59
UID: SDOC-SRS-184
STATUS: Active
TITLE: Three conventions for meta fields
STATEMENT: >>>
StrictDoc shall support reading out SDoc nodes out of Markdown sections arranged in the following way:

1) Requirements with meta-information stored in bullet point list:

.. code-block:: markdown

    ### Requirement title

    - **MID**: abcdabcdabcdabcdabcdabcdabcdabcdabcd
    - **UID**: REQ-001
    - **Status**: Draft

     System A shall do B.

When a Markdown title is followed by a full empty line followed by a bullet list and the bullet list follows the format ``- **<Name>**: <Value>``, the bullet list must be treated as a list of meta fields. The bullet list is terminated by one empty line.

2) Requirements with meta-information stored in consecutive lines separated by the "\\" character:

.. code-block:: markdown

    ### Requirement title

    **MID**: abcdabcdabcdabcdabcdabcdabcdabcdabcd \
    **UID**: REQ-001 \
    **Status**: Draft

    System A shall do B.

When a Markdown title is followed by a full empty line followed by list of lines in the format ``**<Name>**: <Value> \``, the list must be treated as a list of meta fields.
The line list is terminated by one empty line. The last line shall not end with a "\" character.

3) Requirements with meta-information stored in consecutive lines separated by the two empty space characters (as officially supported by Markdown):

.. code-block:: markdown

    ### Requirement title

    **MID**: abcdabcdabcdabcdabcdabcdabcdabcdabcd<two spaces>
    **UID**: REQ-001<two spaces>
    **Status**: Draft<two spaces>

    System A shall do B.

When a Markdown title is followed by a full empty line followed by list of lines in the format ``**<Name>**: <Value><two spaces>``, the list must be treated as a list of meta fields. The list is terminated by one empty line.

Each given node must follow only one of these three syntaxes. If StrictDoc encounters that a single node has more one or more fields of a mixed style, it must give up parsing this node as a valid node, and treat it as a non-normative SECTION/TEXT node.

As of Markdown MVP, the default and preferred syntax: shall be #2 with backslashes.
<<<

[REQUIREMENT]
MID: 111111ede0f2477181bfc7667684df59
UID: SDOC-SRS-185
STATUS: Active
TITLE: Valid formats for multi-line fields
STATEMENT: >>>
StrictDoc shall recognize SDoc node multiline fields from the following three formats

1) Explicit field name:

.. code-block:: markdown

    ### Requirement title

    - **MID**: abcdabcdabcdabcdabcdabcdabcdabcdabcd

     **Statement**: System A shall do B.

2) Explicit field name with a line break:

.. code-block:: markdown

    ### Requirement title

    - **MID**: abcdabcdabcdabcdabcdabcdabcdabcdabcd

     **Statement**:

     System A shall do B.

3) Implicit field name with a line break:

.. code-block:: markdown

    ### Requirement title

    **MID**: abcdabcdabcdabcdabcdabcdabcdabcdabcd

    System A shall do B.

    **Rationale**: This requirement is important because XYZ.

In this case, StrictDoc shall recognize the ``System A shall do B.`` as if it was written as ``**Statement**: System A shall do B.`` and recognize the rationale part as an explicitly written multiline field.

As of Markdown MVP, the default and preferred syntax shall be:

- #1 for values with single-line or single-paragraph/block strings.
- #2 for values with multiple markdown blocks separated by full empty lines.
<<<

[REQUIREMENT]
MID: 121eb00caee34e3fa6eaa683f211a472
UID: SDOC-SRS-202
STATUS: Active
TITLE: Support node parent relations
STATEMENT: >>>
StrictDoc shall support node relations in Markdown using the meta field:

.. code-block:: markdown

    **Relations**: <UID-1>, <UID-2>, ...

When reading Markdown:
- Each UID from the Relations field shall be converted to a relation with TYPE: Parent and VALUE: <UID>.
- All extra spaces shall be normalized before parsing to canonical ``<UID-1>, <UID-2>, ...``.
- The Markdown reader shall not check whether any UID actually exists. This task is deferred to the traceability index builder.

When writing Markdown, SDoc node relations with TYPE: Parent and no ROLE shall be serialized back to the same Relations field as a comma-separated UID list.

NOTE: For MVP, relation roles and Child relation types are out of scope.

NOTE: If the Relations field is not placed as the meta field but as the content field, StrictDoc shall raise a ``StrictDocSemanticError``.
<<<

[REQUIREMENT]
MID: 84df59ede0f2477181bfc7667684df59
UID: SDOC-SRS-193
STATUS: Active
TITLE: Valid SDoc node criteria
STATEMENT: >>>
StrictDoc shall recognize a Markdown node as a valid SDoc node when the Markdown node meets the following criteria:

- The node has one of the meta-fields: MID or UID.
- The node has an explicit or implicit content field.
- All node fields, meta or content, have a valid syntax.
- All node fields, meta or content, are valid default SDoc grammar fields.
<<<

[REQUIREMENT]
MID: 2f3a565aa60340369689eef45cbe7c9c
UID: SDOC-SRS-200
STATUS: Active
TITLE: Valid SDoc document root node
STATEMENT: >>>
StrictDoc shall recognize a root Markdown node as a valid SDoc document node when the said Markdown node meets the following criteria:

- The node has zero or more valid meta-fields.
- The valid metafields must satisfy [LINK: SDOC-SRS-194] and be formatted according to one meta syntax from [LINK: SDOC-SRS-184].

**Example: Valid DOCUMENT (title and metadata) + SECTION:**

.. code-block:: markdown

    # Document title

    **MID**: abcdabcdabcdabcdabcdabcdabcdabcdabcd \
    **UID**: DOC-001 \
    **Author**: John Doe

    ## Hello world

Such a description shall translate to an SDoc document with:

- DOCUMENT node with a title "Document title" and meta fields (MID, UID, Author).
- SECTION node with a title "Hello world".

**Example: Valid DOCUMENT (title and metadata) + TEXT:**

.. code-block:: markdown

    # Document title

    **MID**: abcdabcdabcdabcdabcdabcdabcdabcdabcd \
    **UID**: DOC-001 \
    **Author**: John Doe

    Hello world.

Such a description shall translate to an SDoc document with:

- DOCUMENT node with a title "Document title" and meta fields (MID, UID, Author).
- TEXT node with a statement "Hello world.".

**Example: Valid DOCUMENT (title, no metadata) + TEXT:**

.. code-block:: markdown

    # Document title

    MID: abc

    Hello world.

Such a description shall translate to an SDoc document with:

- DOCUMENT node with a title "Document title" and no meta fields.
- TEXT node with a statement "MID: abc\\n\\nHello world.".
<<<

[REQUIREMENT]
MID: 11133111634c493dbc771ae4c8bc3b14
UID: SDOC-SRS-190
STATUS: Active
TITLE: Reading rules — Default grammar for MVP
STATEMENT: >>>
When a parsing Markdown file, StrictDoc shall generate an SDoc document using the default SDoc grammar according to the following rules:

- The only supported node for MVP shall be REQUIREMENT, TEXT and SECTION nodes with no other nodes supported.
- A valid SDoc node shall be recognized as REQUIREMENT. The Markdown's node title becomes the REQUIREMENT node's TITLE.
- If a Markdown node cannot be recognized as a valid SDoc node, the node shall recognize the said Markdown node's title as a SECTION node with a TITLE field set to the title and the node's body as a regular (non-normative) TEXT SDoc node, not as a normative SDoc node. The TEXT node's statement shall contain the Markdown node's body.
- All field names shall be capitalized when created to SDoc field objects. For example, ``Statement`` becomes ``STATEMENT``. At the same time, the original field names must be written to the document's grammar as-is. For example, a ``**Rationale**:`` becomes ``RATIONALE`` in the SDoc field name and ``Rationale`` in the human title.
- StrictDoc shall defer the validation of MID/UID uniqueness across nodes to the TraceabilityIndexBuilder class.
- If a given field name appears more than once in a node, StrictDoc shall raise a StrictDocSemanticError.
- If a node is otherwise invalid and also has duplicate fields, the parser shall treat this node as SECTION and TEXT without raising errors.
- All SDoc node fields, REQUIREMENT/TEXT/SECTION, must store all field values' Markdown content verbatim, without any pre-processing. This includes preserving original whitespace/line endings exactly.
<<<

[REQUIREMENT]
MID: 44c2dffd898345f39a384bcdacc01b5e
UID: SDOC-SRS-199
STATUS: Active
TITLE: Reading rules — Node hierarchy
STATEMENT: >>>
When a parsing Markdown file, StrictDoc shall generate an SDoc document using the default SDoc grammar according to the following rules:

- The first content of a Markdown file shall always be a level 1 ``#`` node with the document title, followed by an optional set of metafields that translate to SDoc document meta (DocumentConfig/custom_metadata). The syntax for metafields shall be the same to meta fields of a regular markdown node. For MVP, all metafields shall be written as custom_metadata, with no reserved fields are considered.

- When the root L1 document title node with (optional meta fields) are recognized, StrictDoc shall treat all following text as a TEXT node until any other header node starts.

- If StrictDoc can recognize the root L1 document node title but no valid metadata, StrictDoc shall treat all following text as a TEXT node until any other header node starts.

- When root metadata has a valid syntax but has invalid semantics (duplicated fields), StrictDoc shall raise StrictDocSemanticError.

- No other node can be at level 1 except the document title, otherwise StrictDocSemanticError must be raised.

- The Markdown node hierarchy shall be strictly consecutive in forward direction:

  - If a node level forward jump is encountered, for example L1->L3, StrictDoc shall raise a StrictDocSemanticError, regardless of whether the node is valid SDoc node or invalid.

- The node level jumps in backward direction, for example L4->L2, are allowed if the node with a lower level results at level 2 or higher.
<<<

[REQUIREMENT]
MID: c144739494ad4f75b65b9286248005eb
UID: SDOC-SRS-198
STATUS: Active
TITLE: Writing rules — Default grammar for MVP
STATEMENT: >>>
When writing an SDoc document to a markdown file, StrictDoc shall generate the Markdown markup according to the following rules:

- The meta fields shall be written:

  - Using the format #2 for new documents not coming from file system (using backslashes for all meta-field lines but last one).
  - Using the format that was auto-detected during reading a Markdown file in case the file is already on the disk and follows a certain convention. The detection shall be detected at a file level and memorized individually by each SDoc document.

- The content fields shall be written using formats #1 (Explicit field name) for single-paragraph fields and #2 (Explicit field name with a line break) for multi-paragraph fields. A multi-paragraph field is one that results in multiple markdown paragraphs/blocks each separated visually by a full empty line.

- StrictDoc shall write the SDoc fields as Markdown fields based on SDoc human title as recorded in the document grammar element field human title. If a human title is missing in the grammar, the field name shall be used.

- All fields shall be printed in the same order like they are stored in an SDoc node. Meta vs content decision shall be based on a standard SDocNode/GrammarElement decision for multiline index.

- The node level shall be used for defining the Markdown node level. The document title becomes the top-level section level 1. SDoc node level 1 becomes ``##``, level 2 becomes ``###``, etc.
<<<

[REQUIREMENT]
MID: 987111ede0f2477181bfc7667684df59
UID: SDOC-SRS-187
STATUS: Active
TITLE: Robust Markdown backend
STATEMENT: >>>
StrictDoc shall employ a well-maintained Markdown library with Python support.
<<<

[[/SECTION]]

[[SECTION]]
MID: 34b4abc6bb4649de9e56af31c229b0d1
UID: SECTION-SRS-Graph-database
TITLE: Graph database

[REQUIREMENT]
MID: 2c8d7940a23c443f81a7eb373340894e
UID: SDOC-SRS-28
STATUS: Active
TITLE: Traceability index
STATEMENT: >>>
StrictDoc shall maintain a complete Traceability Index of all documentation- and requirements-related information available in a project tree.
<<<
RELATIONS:
- TYPE: Parent
  VALUE: SDOC-SSS-7

[REQUIREMENT]
MID: 272b8933276d4cd48a78fcfa11899573
UID: SDOC-SRS-29
STATUS: Active
TITLE: Uniqueness UID in tree
STATEMENT: >>>
For each requirement node, the Traceability Index shall ensure its uniqueness throughout the node's lifecycle.
<<<
RATIONALE: >>>
The requirement ensures that the Traceability Index takes of care of validating the uniqueness of all nodes in a document/requirements graph.
<<<
RELATIONS:
- TYPE: Parent
  VALUE: SDOC-SSS-89
- TYPE: Parent
  VALUE: SDOC-SSS-94

[REQUIREMENT]
MID: 8330d61fd5b1438fa90f127f88903a0d
UID: SDOC-SRS-30
STATUS: Active
TITLE: Detect links cycles
STATEMENT: >>>
The Traceability Index shall detect cycles between requirements.
<<<
RELATIONS:
- TYPE: Parent
  VALUE: SDOC-SSS-47
- TYPE: File
  FORMAT: Sourcecode
  VALUE: strictdoc/core/tree_cycle_detector.py
- TYPE: Parent
  VALUE: SDOC-SSS-94

[REQUIREMENT]
MID: 07a1e7bef11d4fcca86cd31ee5245d8d
UID: SDOC-SRS-32
STATUS: Active
TITLE: Link document nodes
STATEMENT: >>>
The Traceability Index shall recognize and maintain the relations between all documents of a project tree.
<<<
RATIONALE: >>>
The relations between all documents are a summary of all relations between these documents' requirements. This information is useful for:

1) Structural analysis of a requirements/documents graph.
2) Incremental regeneration of only those documents whose content was modified.
<<<
RELATIONS:
- TYPE: Parent
  VALUE: SDOC-SSS-47
- TYPE: Parent
  VALUE: SDOC-SSS-13
- TYPE: Parent
  VALUE: SDOC-SSS-14

[REQUIREMENT]
MID: 2dad5f293bc442eaa98859c4b5eac0d5
UID: SDOC-SRS-102
STATUS: Active
TITLE: Automatic resolution of reverse relations
STATEMENT: >>>
The StrictDoc's graph database shall maintain the requirement relations and their reverse relations as follows:

- For a Parent relation, the database shall calculate the reverse Child relation.
- For a Child relation, the database shall calculate the reverse Parent relation.
<<<
RATIONALE: >>>
The calculation of the reverse relations allows the user interface code to get and display both requirement's parent and child relations.
<<<
COMMENT: >>>
Example: If a child requirement REQ-002 has a parent requirement REQ-001, the graph database first reads the link ``REQ-002 -Parent> REQ-001``, then it creates a corresponding ``REQ-001 -Child> REQ-002`` on the go. Both relations can be queried as follows, in pseudocode:

.. code-block::

    get_parent_requirements(REQ-002) == [REQ-001]
    get_children_requirements(REQ-001) == [REQ-002]
<<<
RELATIONS:
- TYPE: Parent
  VALUE: SDOC-SSS-71
- TYPE: Parent
  VALUE: SDOC-SSS-48

[[/SECTION]]

[[SECTION]]
MID: 4dce611287954289b1c2a6a15c413611
TITLE: Documentation tree

[REQUIREMENT]
MID: 50b2d5d6eb1140f0a2b980203468a5f7
UID: SDOC-SRS-115
STATUS: Active
TITLE: Finding documents recursively
STATEMENT: >>>
StrictDoc shall discover SDoc documents recursively based on a specified input path.
<<<
RATIONALE: >>>
Recursive search allows working with documents located in multiple folders, potentially spanning over several Git repositories.
<<<
RELATIONS:
- TYPE: Parent
  VALUE: SDOC-SSS-34
- TYPE: Parent
  VALUE: DO178-3

[[/SECTION]]

[[SECTION]]
MID: fcbf717009ce4cb2a8def7eb7b377654
UID: SECTION-SRS-Web-HTML-frontend
TITLE: Web/HTML frontend

[[SECTION]]
MID: a3603184d571449792f5cd752c978686
UID: SECTION-SRS-General-export-requirements-2
TITLE: General export requirements

[REQUIREMENT]
MID: 37f17fdd57ff47e9b7f4147adaeabde1
UID: SDOC-SRS-49
STATUS: Active
TITLE: Export to static HTML website
STATEMENT: >>>
StrictDoc shall support generating requirements documentation into static HTML.
<<<
RELATIONS:
- TYPE: Parent
  VALUE: SDOC-SSS-30
- TYPE: File
  VALUE: strictdoc/export/html/html_generator.py
- TYPE: File
  VALUE: strictdoc/core/actions/export_action.py

[REQUIREMENT]
MID: 37399be2a8ac46889e3437209f9dffa9
UID: SDOC-SRS-50
STATUS: Active
TITLE: Web interface
STATEMENT: >>>
StrictDoc shall provide a web interface.
<<<
RELATIONS:
- TYPE: Parent
  VALUE: SDOC-SSS-31
- TYPE: Parent
  VALUE: DO178-6
- TYPE: Parent
  VALUE: SDOC-SSS-79
- TYPE: Parent
  VALUE: SDOC-SSS-80
- TYPE: File
  VALUE: strictdoc/server/app.py
- TYPE: File
  VALUE: strictdoc/server/routers/main_router.py

[REQUIREMENT]
MID: f97dc050ddab4a08bf1689200118faaa
UID: SDOC-SRS-123
STATUS: Active
TITLE: Multi-user editing of documents
STATEMENT: >>>
StrictDoc shall support concurrent use and editing of a single StrictDoc web server instance by multiple users.
<<<
RELATIONS:
- TYPE: Parent
  VALUE: DO178-17
- TYPE: Parent
  VALUE: SDOC-SSS-81

[REQUIREMENT]
MID: 8811f0ef33de4365bc66a602a8c184f6
UID: SDOC-SRS-48
STATUS: Active
TITLE: Preserve generated file names
STATEMENT: >>>
For all export operations, StrictDoc shall maintain the original filenames of the documents when producing output files.
<<<
RATIONALE: >>>
Name preservation helps to visually identify which input file an output file corresponds to.
<<<
RELATIONS:
- TYPE: Parent
  VALUE: SDOC-SSS-80

[[/SECTION]]

[[SECTION]]
MID: b99ebebdadb94fec968785429cef9002
UID: SECTION-SRS-Screen-Project-tree
TITLE: Screen: Project tree

[REQUIREMENT]
MID: 100fa410f4b443e69c48738899cfb5bd
UID: SDOC-SRS-53
STATUS: Active
TITLE: View project tree
STATEMENT: >>>
StrictDoc's "Project tree" screen shall provide browsing of a documentation project tree.
<<<
RATIONALE: >>>
This screen is the main tool for visualizing the project tree structure.
<<<
RELATIONS:
- TYPE: File
  FORMAT: Sourcecode
  VALUE: strictdoc/export/html/generators/document_tree.py
- TYPE: Parent
  VALUE: SDOC-SSS-91

[REQUIREMENT]
MID: eb04abcfd64146f3b7be509afd1693f9
UID: SDOC-SRS-107
STATUS: Active
TITLE: Create document
STATEMENT: >>>
StrictDoc's Project Tree screen shall allow creating documents.
<<<
RELATIONS:
- TYPE: Parent
  VALUE: SDOC-SSS-3

[REQUIREMENT]
MID: de7cda1156e043d7999933a2df630a30
UID: SDOC-SRS-108
STATUS: Active
TITLE: Delete document
STATEMENT: >>>
StrictDoc's Project Tree screen shall allow deleting documents.
<<<
RELATIONS:
- TYPE: Parent
  VALUE: SDOC-SSS-3

[[/SECTION]]

[[SECTION]]
MID: 185cfc2d1ed4429ebaf0689f70a8cb0a
UID: SECTION-SRS-Screen-Document-DOC
TITLE: Screen: Document (DOC)

[REQUIREMENT]
MID: 93e6f08c949a48fa98cf86288492d8fd
UID: SDOC-SRS-201
STATUS: Active
TITLE: Format-specific document handling
STATEMENT: >>>
StrictDoc's Document screen shall arrange all CRUD operations according to the input document format.

Example: If an SDoc document is read from a Markdown file using a dedicated reader, it shall be written back using a Markdown writer.
<<<
RELATIONS:
- TYPE: Parent
  VALUE: SDOC-SSS-3

[REQUIREMENT]
MID: 9c962637ef7f45b6af6c83964b0a06d9
UID: SDOC-SRS-54
STATUS: Active
TITLE: Read document
STATEMENT: >>>
StrictDoc's Document screen shall allow reading documents.
<<<
RELATIONS:
- TYPE: Parent
  VALUE: SDOC-SSS-3

[REQUIREMENT]
MID: 201187122be14ea48d69106d396c6790
UID: SDOC-SRS-106
STATUS: Active
TITLE: Create node
STATEMENT: >>>
StrictDoc's Document screen shall allow creating document nodes.
<<<
RELATIONS:
- TYPE: Parent
  VALUE: SDOC-SSS-3

[REQUIREMENT]
MID: 9b291b5df5914f13b23fb8c367be0a24
UID: SDOC-SRS-161
STATUS: Active
TITLE: Clone node from existing node
STATEMENT: >>>
StrictDoc shall support cloning nodes from existing nodes.
<<<
RATIONALE: >>>
Simplifies the creation of similar nodes.
<<<

[REQUIREMENT]
MID: 13968ae160744e10ba8979eaee2f4f54
UID: SDOC-SRS-55
STATUS: Active
TITLE: Update node
STATEMENT: >>>
StrictDoc's Document screen shall allow update document content.
<<<
RELATIONS:
- TYPE: Parent
  VALUE: SDOC-SSS-4

[REQUIREMENT]
MID: 0ec87f08626a4839b5951d98fef9e0e1
UID: SDOC-SRS-162
STATUS: Active
TITLE: Delete node
STATEMENT: >>>
StrictDoc's Document screen shall support the deletion of document nodes.
<<<

[REQUIREMENT]
MID: b805e36294764e8f8cb5a88ab8fa0467
UID: SDOC-SRS-159
STATUS: Active
TITLE: Create node relation
STATEMENT: >>>
StrictDoc's Document screen shall creating updating node relations.
<<<
RELATIONS:
- TYPE: Parent
  VALUE: SDOC-SSS-7

[REQUIREMENT]
MID: f32c091454c94bc5bd2091e2c4f38582
UID: SDOC-SRS-158
STATUS: Active
TITLE: Update node relation
STATEMENT: >>>
StrictDoc's Document screen shall allow updating node relations.
<<<
RELATIONS:
- TYPE: Parent
  VALUE: SDOC-SSS-7

[REQUIREMENT]
MID: edc02a3a97704007b70b93102c76b278
UID: SDOC-SRS-92
STATUS: Active
TITLE: Move requirement / section nodes within document
STATEMENT: >>>
StrictDoc's Document screen shall provide a capability to move the nodes within a document.
<<<
RATIONALE: >>>
Moving the nodes within a document is a convenience feature that speeds up the requirements editing process significantly.
<<<
RELATIONS:
- TYPE: Parent
  VALUE: SDOC-SSS-5

[REQUIREMENT]
MID: 197e00dd3b1d42309250c89de23ea51b
UID: SDOC-SRS-56
STATUS: Active
TITLE: Edit Document grammar
STATEMENT: >>>
StrictDoc's screen shall allow editing a document's grammar.
<<<
RATIONALE: >>>
Editing document grammar allows a user to customize the requirements fields.
<<<
RELATIONS:
- TYPE: Parent
  VALUE: SDOC-SSS-62

[REQUIREMENT]
MID: 2706ac7ccb8148edb7b200a1b78c25d6
UID: SDOC-SRS-57
STATUS: Active
TITLE: Edit Document options
STATEMENT: >>>
StrictDoc's Document screen shall provide controls for configuring the document-specific options.
<<<
RELATIONS:
- TYPE: Parent
  VALUE: SDOC-SSS-93

[REQUIREMENT]
MID: d64f7a0f6ba54672a62634304c54e2d4
UID: SDOC-SRS-96
STATUS: Active
TITLE: Auto-generate requirements UIDs
STATEMENT: >>>
StrictDoc's Document screen shall provide controls for automatic generation of requirements UIDs.
<<<
RELATIONS:
- TYPE: Parent
  VALUE: SDOC-SSS-6
- TYPE: Parent
  VALUE: SDOC-SSS-80
- TYPE: File
  FORMAT: Sourcecode
  VALUE: strictdoc/core/analyzers/document_uid_analyzer.py
- TYPE: File
  FORMAT: Sourcecode
  VALUE: strictdoc/commands/manage_autouid_command.py

[REQUIREMENT]
MID: 956371b6a7824d0b91caa5603faeeae2
UID: SDOC-SRS-120
STATUS: Active
TITLE: Auto-completion for requirements UIDs
STATEMENT: >>>
StrictDoc's Document screen shall provide controls for automatic completion of requirements UIDs.
<<<
COMMENT: >>>
The automatic completion can be especially useful when a user has to fill in a parent relation UID.
<<<
RELATIONS:
- TYPE: Parent
  VALUE: SDOC-SSS-6
- TYPE: Parent
  VALUE: DO178-14
- TYPE: Parent
  VALUE: SDOC-SSS-80

[REQUIREMENT]
MID: 738b63b7f55b43eb99f5600bd65f5ba7
UID: SDOC-SRS-59
STATUS: Active
TITLE: Buttons to copy text to buffer
STATEMENT: >>>
StrictDoc shall provide a "copy text to buffer" button for all requirement's text fields.
<<<
RELATIONS:
- TYPE: Parent
  VALUE: SDOC-SSS-80
- TYPE: File
  VALUE: strictdoc/export/html/_static/controllers/copy_to_clipboard_controller.js

[[/SECTION]]

[[SECTION]]
MID: 2b5d74dafd6d43f4bab4c05ed4da6f0d
UID: SECTION-SRS-Screen-Table-TBL
TITLE: Screen: Table (TBL)

[REQUIREMENT]
MID: e12b4c5b4f13444d99279ab445df5bcc
UID: SDOC-SRS-62
STATUS: Active
TITLE: View TBL screen
STATEMENT: >>>
StrictDoc's Table screen shall allow reading documents in a table-like manner.
<<<
RELATIONS:
- TYPE: Parent
  VALUE: SDOC-SSS-73
- TYPE: File
  VALUE: strictdoc/export/html/generators/document_table.py

[[/SECTION]]

[[SECTION]]
MID: 3c589969eb6a41c19b1dd246dabadbc8
UID: SECTION-SRS-Screen-Traceability-TR
TITLE: Screen: Traceability (TR)

[REQUIREMENT]
MID: 35d4c1dd30814c2a80918a90081a88b7
UID: SDOC-SRS-65
STATUS: Active
TITLE: View TR screen
STATEMENT: >>>
StrictDoc shall provide a single document-level traceability screen.

NOTE: This screen helps to read a document like a normal document while the traceability to this document's parent and child elements is visible at the same time.
<<<
RELATIONS:
- TYPE: Parent
  VALUE: SDOC-SSS-28

[[/SECTION]]

[[SECTION]]
MID: 9d337068b6a940b7a98d40697ea200a8
UID: SECTION-SRS-Screen-Deep-traceability-DTR
TITLE: Screen: Deep traceability (DTR)

[REQUIREMENT]
MID: 48bc17d898c94605b17d0267480f57ee
UID: SDOC-SRS-66
STATUS: Active
TITLE: View DTR screen
STATEMENT: >>>
StrictDoc shall provide a deep traceability screen.
<<<
RELATIONS:
- TYPE: Parent
  VALUE: DO178-12

[[/SECTION]]

[[SECTION]]
MID: 181dfbcbbfac41e18f7fb09af0df8f4e
TITLE: Screen: HTML2PDF

[REQUIREMENT]
MID: f2fd90ad8a2946e7b085233a9c7a8a75
UID: SDOC-SRS-51
STATUS: Active
TITLE: Export to HTML content to PDF (HTML2PDF)
STATEMENT: >>>
StrictDoc shall allow exporting documents and entire documentation trees to PDF.
<<<
RATIONALE: >>>
As required by the parent requirement, PDF is one of the most common documentation formats.
<<<
RELATIONS:
- TYPE: Parent
  VALUE: DO178-5
- TYPE: Parent
  VALUE: SDOC-SSS-96

[REQUIREMENT]
MID: 6cfcb21b3f1949f49d13af6b00d3d37a
UID: SDOC-SRS-160
STATUS: Active
TITLE: Custom PDF export template
STATEMENT: >>>
StrictDoc shall support the customization of the PDF export template.
<<<

[[/SECTION]]

[[SECTION]]
MID: ddf15b3113a54107979752ec192e2ded
TITLE: Screen: Project statistics

[REQUIREMENT]
MID: 19f7c2d35237423e950584a4a7aa95a7
UID: SDOC-SRS-97
STATUS: Active
TITLE: Display project statistics
STATEMENT: >>>
StrictDoc shall provide a Project Statistics screen that displays the following project information:

- Project title
- Date of generation
- Git revision
- Total documents
- Total requirements
- Requirements status breakdown
- Total number of TBD/TBC found in documents.
<<<
RATIONALE: >>>
TBD
<<<
RELATIONS:
- TYPE: Parent
  VALUE: SDOC-SSS-49
- TYPE: Parent
  VALUE: DO178-12
- TYPE: Parent
  VALUE: SDOC-SSS-29
- TYPE: File
  VALUE: strictdoc/export/html/generators/project_statistics.py

[REQUIREMENT]
MID: 7968fb7612f64504b5a430ccbffe80f1
UID: SDOC-SRS-154
STATUS: Active
TITLE: Support for user-provided custom statistics generators
STATEMENT: >>>
StrictDoc shall support customization of the project statistics screen, enabling users to define and display their own project-specific statistics.
<<<
RATIONALE: >>>
Projects often have unique traceability and reporting requirements, and supporting custom statistics allows StrictDoc to display metrics that are most relevant to each project's context.
<<<
RELATIONS:
- TYPE: Parent
  VALUE: SDOC-SSS-49

[[/SECTION]]

[[SECTION]]
MID: d84e3a79b3e443cabe96d7c18ea5d322
TITLE: Screen: Document tree map

[REQUIREMENT]
MID: 1520fa85ed7a4f1aa80c49ed858f402f
UID: SDOC-SRS-157
STATUS: Active
TITLE: Tree map
STATEMENT: >>>
StrictDoc shall provide a tree map screen, visualizing the following information:

- Document tree map
- Requirements coverage by source code
- Requirements coverage by test files.
<<<
RATIONALE: >>>
Enables the visualization and browsing of the overall document tree and requirements coverage information.
<<<
RELATIONS:
- TYPE: Parent
  VALUE: SDOC-SSS-29

[[/SECTION]]

[[SECTION]]
MID: 63df985038374acb82e9b4185eff5a7e
TITLE: Screen: Source coverage

[REQUIREMENT]
MID: 3aeb1eea0dba4041a9161a1a8d291999
UID: SDOC-SRS-35
STATUS: Active
TITLE: Project source code coverage
STATEMENT: >>>
StrictDoc shall generate project source code coverage information.

NOTE: Source code information can be visualized using both web or CLI interfaces.
<<<
RELATIONS:
- TYPE: Parent
  VALUE: SDOC-SSS-72
- TYPE: Parent
  VALUE: DO178-13
- TYPE: File
  FORMAT: Sourcecode
  VALUE: strictdoc/export/html/generators/source_file_coverage.py

[[/SECTION]]

[[SECTION]]
MID: 9c19eea544ec4d90bb65fd8fd9b13cc4
TITLE: Screen: Single source file coverage

[REQUIREMENT]
MID: 56ecfb19152e45b09c0e55de2d1d5f05
UID: SDOC-SRS-36
STATUS: Active
TITLE: Single source file coverage
STATEMENT: >>>
StrictDoc shall generate single file traceability information.
<<<
RATIONALE: >>>
With this capability in place, it is possible to focus on a single implementation file's links to requirements which helps in the code reviews and inspections.
<<<
RELATIONS:
- TYPE: Parent
  VALUE: SDOC-SSS-72
- TYPE: File
  FORMAT: Sourcecode
  VALUE: strictdoc/export/html/generators/source_file_view_generator.py

[[/SECTION]]

[[SECTION]]
MID: 14ad600308434e6baaeef02d3e90b720
TITLE: Screen: Traceability matrix

[REQUIREMENT]
MID: 167f6fe66d7247a6bf628ed6c1949275
UID: SDOC-SRS-112
STATUS: Active
TITLE: Traceability matrix
STATEMENT: >>>
StrictDoc shall provide a traceability matrix screen.
<<<
RELATIONS:
- TYPE: Parent
  VALUE: SDOC-SSS-28
- TYPE: Parent
  VALUE: DO178-10
- TYPE: Parent
  VALUE: DO178-12
- TYPE: File
  VALUE: strictdoc/export/html/generators/traceability_matrix.py

[[/SECTION]]

[[SECTION]]
MID: 544f8ffed8604e63a269a3f953681163
TITLE: Screen: Project tree diff

[REQUIREMENT]
MID: aef80cc1a3144564bf23bf3c2a1cfd7f
UID: SDOC-SRS-111
STATUS: Active
TITLE: Project tree diff
STATEMENT: >>>
StrictDoc shall provide a project tree diff screen.
<<<
RELATIONS:
- TYPE: Parent
  VALUE: SDOC-SSS-75
- TYPE: Parent
  VALUE: SDOC-SSS-74
- TYPE: Parent
  VALUE: DO178-15
- TYPE: File
  VALUE: strictdoc/git/change_generator.py
- TYPE: File
  VALUE: strictdoc/git/project_diff_analyzer.py

[[/SECTION]]

[[SECTION]]
MID: 8380fb39beb04d1c9370733bcfafbc01
TITLE: Content search

[REQUIREMENT]
MID: 3e85dd6bf05a4cecb8e070fd81aa333a
UID: SDOC-SRS-155
STATUS: Active
TITLE: Content search
STATEMENT: >>>
StrictDoc shall provide searching documentation content with queries via a search bar.
<<<
RATIONALE: >>>
As per the parent requirement, a search bar with query support enables users to interactively find specific content without navigating the entire documentation tree.
<<<
RELATIONS:
- TYPE: Parent
  VALUE: SDOC-SSS-95

[[/SECTION]]

[[/SECTION]]

[[SECTION]]
MID: 2d4dc6fc901f4b28aaf414fcfbdfabca
UID: SECTION-SRS-Requirements-to-source-traceability
TITLE: Requirements-to-source traceability

[REQUIREMENT]
MID: 221b544dab2e4b96be124e1caf84a7c2
UID: SDOC-SRS-33
STATUS: Active
TITLE: Link requirements with source files
STATEMENT: >>>
StrictDoc shall support bi-directional linking requirements with source files.
<<<
RELATIONS:
- TYPE: Parent
  VALUE: SDOC-SSS-72

[[SECTION]]
MID: 2f63252320d546d88462849b521f45ba
TITLE: Language-aware parsing of source code

[REQUIREMENT]
MID: 79a8080f6e41485f9835ccda067b34bc
UID: SDOC-SRS-142
TITLE: Language-aware parsing of source code
STATEMENT: >>>
StrictDoc shall support parsing the most commonly used formats and programming languages to the Abstract Syntax Tree (AST) level.

The format examples: C, C++, Python, Rust, Ada, Robot, Gherkin, etc.
<<<
RATIONALE: >>>
StrictDoc must be capable of traversing the AST of common formats and programming languages to identify and extract function and class markers.
<<<

[REQUIREMENT]
MID: 85a8080f8441485f9111ccda063b34bc
UID: SDOC-SRS-146
STATUS: Active
TITLE: Language-aware parsing of C/C++ code
STATEMENT: >>>
StrictDoc shall support parsing the C and C++ source files which includes:

- Recognizing functions and their Doxygen comments.
- Recognizing function declarations and function definitions.
<<<
RATIONALE: >>>
C and C++ languages are common languages for embedded and general systems programming. These languages have to be handled with a dedicated parser because of these languages' specifics.
<<<

[REQUIREMENT]
MID: 3456080f1358485f9bacdcda063b34bc
UID: SDOC-SRS-147
STATUS: Active
TITLE: Language-aware parsing of Python code
STATEMENT: >>>
StrictDoc shall support parsing the Python source files which includes:

- Recognizing Python functions, including nested functions.
- Recognizing Python classes, including nested classes.
- Recognizing decorated functions.
<<<
RATIONALE: >>>
Python language has to be handled with a dedicated parser because of this language's specifics.
<<<

[REQUIREMENT]
MID: 9183080f1358485f9bacdcda0635109
UID: SDOC-SRS-148
STATUS: Active
TITLE: Language-aware parsing of Robot framework code
STATEMENT: >>>
StrictDoc shall support parsing the Robot framework test files.
<<<
RATIONALE: >>>
Robot framework's markup has to be handled with a dedicated parser because of this language's specifics.
<<<

[[/SECTION]]

[[SECTION]]
MID: e18dcfcb9b99459d9c7f560f35d01ff8
TITLE: Language-aware parsing of Rust source code

[REQUIREMENT]
MID: d83cab2dcd014d328b348acc37c6f4a6
UID: SDOC-SRS-164
TITLE: Auto-scoped relation markers in Rust docs
STATEMENT: >>>
If a StrictDoc relation marker is inside a `Rust doc comment`_, the marker scope shall be set to exact the item the Rust
language defines as target of the containing doc comment. The :code:`@relation(scope=...)` parameter shall therefore
be optional and shall be ignored if provided.

.. code-block:: rust
   :number-lines:

   /// @relation(REQ-1)
   impl Foo {

       /// @relation(REQ-2)
       fn foo() {
       }
   }

In the given example, the first marker shall link REQ-1 to the :code:`impl Foo` implementation,
highlighting lines 1 to 7. The second marker shall link REQ-2 to the :code:`fn foo()` function,
highlighting lines 4 to 6.

.. _Rust doc comment: https://doc.rust-lang.org/rust-by-example/meta/doc.html#doc-comments
<<<
COMMENT: >>>
Note that doc comments are syntactic sugar for `doc attribute`_ s, which shall also be supported.
To figure detailed doc comment rules from the rust-lang specification it's sometimes useful
to check for general attribute rules, if explicit doc comment rules are missing.

.. _doc attribute: https://doc.rust-lang.org/rustdoc/write-documentation/the-doc-attribute.html
<<<
RELATIONS:
- TYPE: Parent
  VALUE: SDOC-SRS-34
- TYPE: Parent
  VALUE: SDOC-SRS-137

[REQUIREMENT]
MID: 91c7b9fd9c514327bb012639cdf1515b
UID: SDOC-SRS-165
TITLE: Inner doc attributes
STATEMENT: >>>
StrictDoc shall support relation markers in inner_ `doc attribute`_ s.

.. _inner: https://doc.rust-lang.org/reference/attributes.html#r-attributes.inner
.. _doc attribute: https://doc.rust-lang.org/rustdoc/write-documentation/the-doc-attribute.html#the-doc-attribute
<<<
RELATIONS:
- TYPE: Parent
  VALUE: SDOC-SRS-164

[REQUIREMENT]
MID: 002bfab5383e4cb785049c4738651f43
UID: SDOC-SRS-166
TITLE: Inner line docs
STATEMENT: >>>
StrictDoc shall support auto-scoped relation relation markers in `inner line docs`_.

.. _inner line docs: https://doc.rust-lang.org/reference/comments.html#grammar-INNER_LINE_DOC
<<<
RELATIONS:
- TYPE: Parent
  VALUE: SDOC-SRS-164

[REQUIREMENT]
MID: d04b97d76cc848f982610035bf7d3dc2
UID: SDOC-SRS-167
TITLE: Inner block docs
STATEMENT: >>>
StrictDoc shall support auto-scoped relation relation markers in `inner block docs`_.

.. _inner block docs: https://doc.rust-lang.org/reference/comments.html#grammar-INNER_BLOCK_DOC
<<<
RELATIONS:
- TYPE: Parent
  VALUE: SDOC-SRS-164

[REQUIREMENT]
MID: 84b351267cfc4e16b3ff2c5db654e9f0
UID: SDOC-SRS-168
TITLE: Outer doc attributes
STATEMENT: >>>
StrictDoc shall support auto-scoped relation markers in outer_ `doc attribute`_ s.

.. _outer: https://doc.rust-lang.org/reference/attributes.html#r-attributes.outer
.. _doc attribute: https://doc.rust-lang.org/rustdoc/write-documentation/the-doc-attribute.html#the-doc-attribute
<<<
RELATIONS:
- TYPE: Parent
  VALUE: SDOC-SRS-164

[REQUIREMENT]
MID: 171978da9f8f4f40b52fb7599caa67e6
UID: SDOC-SRS-169
TITLE: Outer line docs
STATEMENT: >>>
StrictDoc shall support auto-scoped relation markers in `outer line docs`_.

.. _outer line docs: https://doc.rust-lang.org/reference/comments.html#grammar-OUTER_LINE_DOC
<<<
RELATIONS:
- TYPE: Parent
  VALUE: SDOC-SRS-164

[REQUIREMENT]
MID: 1a8d558fbe244621818b6242be365638
UID: SDOC-SRS-170
TITLE: Outer block docs
STATEMENT: >>>
StrictDoc shall support auto-scoped relation markers in `outer block docs`_.

.. _outer block docs: https://doc.rust-lang.org/reference/comments.html#railroad-OUTER_BLOCK_DOC
<<<
RELATIONS:
- TYPE: Parent
  VALUE: SDOC-SRS-164

[REQUIREMENT]
MID: e1be1f38dd374f82abd9691d081f293b
UID: SDOC-SRS-171
TITLE: File, line and range markers
STATEMENT: >>>
StrictDoc shall point to lines and line ranges of Rust code by using file, line and range markers.
These marker types shall be parsed from `regular line and block comments`_.

Note: File markers may also result from the inner doc comments of the top-level module.

.. _regular line and block comments: https://doc.rust-lang.org/rust-by-example/hello/comment.html#comments
<<<
RELATIONS:
- TYPE: Parent
  VALUE: SDOC-SRS-139
- TYPE: Parent
  VALUE: SDOC-SRS-124
- TYPE: Parent
  VALUE: SDOC-SRS-138

[REQUIREMENT]
MID: b9b2e4d377db42f5b3fb7aeabaf3f72a
UID: SDOC-SRS-172
TITLE: Source nodes from doc comments
STATEMENT: >>>
If a Rust doc comments contains custom tags, and the containing Rust source file matches an entry in the
source node configuration, StrictDoc shall create document nodes from the custom tags and automatically
link the created node with the Rust item targeted by the doc comment.
<<<
RELATIONS:
- TYPE: Parent
  VALUE: SDOC-SRS-141

[REQUIREMENT]
MID: 9d7e371ad7a146e1968cd9bbb7a6790f
UID: SDOC-SRS-173
TITLE: Forward relations to Rust items
STATEMENT: >>>
StrictDoc shall support linking from a requirement in SDoc to a language item in Rust code by using a :code:`FILE`
relation of type :code:`FUNCTION`. For example

.. code-block:: strictdoc

   [REQUIREMENT]
   UID: REQ-1
   RELATIONS:
   - TYPE: File
     VALUE: file.rs
     FUNCTION: file::foo

This shall work for all kinds of Rust items that have a `canonical path`_, including const, enum, fn, mod, static,
struct, trait, type, union.

.. _canonical path: https://doc.rust-lang.org/reference/paths.html#canonical-paths
<<<

[REQUIREMENT]
MID: d01b2204fcb44882b991ca11ce567f52
UID: SDOC-SRS-174
TITLE: Forward relation by canonical path
STATEMENT: >>>
The identifier for forward relations shall be the `canonical path`_ as the rustc compiler would set it when invoked for
a single file like

.. code-block:: shell

   rustc --crate-type rlib --emit=obj src/lib.rs

Note: :code:`cargo build` usually result in a different canonical path, since it considers the file position relative to
the crate root. Using a single file as root is a simplification, needed because StrictDoc is unaware of the Rust
file and directory-based module hierarchy.

.. _canonical path: https://doc.rust-lang.org/reference/paths.html#canonical-paths
<<<
COMMENT: >>>
The canonical path of an item can be observed with :code:`objdump -t lib.o --demangle=rust`. For example, given this
source file

.. code-block:: rust
   :number-lines:

   pub mod foo {

       pub trait Foo {
           fn foo(&self) {}
       }

       pub struct Bar(i32);

       impl Foo for Bar {
           fn foo(&self) {}
       }
   }

:code:`objdump` will show

.. code-block:: shell

   <lib::foo::Bar as lib::foo::Foo>::foo

Alas, a forward relation would be

.. code-block:: strictdoc

   [REQUIREMENT]
   UID: REQ-1
   RELATIONS:
   - TYPE: File
     VALUE: file.rs
     FUNCTION: <lib::foo::Bar as lib::foo::Foo>::foo
<<<
RELATIONS:
- TYPE: Parent
  VALUE: SDOC-SRS-173

[REQUIREMENT]
MID: 04b5927294c34710995d3671040dd8ae
UID: SDOC-SRS-175
TITLE: Collapse doc comments
STATEMENT: >>>
Multiple scattered doc comments shall be collapsed as done by the rustdoc_ tool when using the collapse-docs option
to determine the highlight range(s).

For example, rustdoc would collapse alle these comments into the description of :code:`fn foo()`

.. code-block:: rust
   :number-lines:

   /// Some
   /// line

   /// doc,

   /**
     * and some
     * block dock,
     */

   #[doc = "and some"]

   #[doc = "doc attr."]

   fn foo() {
   }

In the given example, the StrictDoc highlight range for the relation marker shall be from line 1 to line 16.

.. _rustdoc: https://github.com/rust-lang/rust/tree/main/src/tools/rustdoc
<<<

[REQUIREMENT]
MID: e67e8258177847138112589e606c0413
UID: SDOC-SRS-176
TITLE: Rust marker descriptions
STATEMENT: >>>
StrictDoc should use the marker labels as rustdoc_ would set them in the description of a documented node.

.. _rustdoc: https://doc.rust-lang.org/stable/rustdoc/
<<<

[REQUIREMENT]
MID: 7bf3f26c335741398a50e9679a0d4c84
UID: SDOC-SRS-177
TITLE: Valid positions of doc comments
STATEMENT: >>>
StrictDoc shall find doc comments where the language allows_ them and ignore those in other positions.

.. _allows: https://doc.rust-lang.org/reference/attributes.html#r-attributes.allowed-position
<<<
COMMENT: >>>
Since doc comments are syntactic sugar for doc attributes, allowed position rules for attributes apply.
<<<

[REQUIREMENT]
MID: 5e9645177af14db7b5fcaba0298a328b
UID: SDOC-SRS-178
TITLE: Inner doc comments for functions
STATEMENT: >>>
StrictDoc shall find inner doc comments in function blocks.
<<<
RELATIONS:
- TYPE: Parent
  VALUE: SDOC-SRS-177

[REQUIREMENT]
MID: b70a27cc49f54b0bb7e7956b055957a4
UID: SDOC-SRS-179
TITLE: Inner doc comments for modules
STATEMENT: >>>
StrictDoc shall find inner doc comments in module blocks.
<<<
RELATIONS:
- TYPE: Parent
  VALUE: SDOC-SRS-177

[REQUIREMENT]
MID: 012e605921954430ab6c11e245fb7378
UID: SDOC-SRS-180
TITLE: Inner doc comments for external blocks
STATEMENT: >>>
StrictDoc shall find inner doc comments in external blocks.
<<<
RELATIONS:
- TYPE: Parent
  VALUE: SDOC-SRS-177

[REQUIREMENT]
MID: 2d955dd847954556aa5a32018a7c41fd
UID: SDOC-SRS-181
TITLE: Inner doc comments for implementation blocks
STATEMENT: >>>
StrictDoc shall find inner doc comments in implementation blocks.
<<<
RELATIONS:
- TYPE: Parent
  VALUE: SDOC-SRS-177

[REQUIREMENT]
MID: ef8849024b78477496620eb1bf081900
UID: SDOC-SRS-182
TITLE: Allowed position for outer docs
STATEMENT: >>>
StrictDoc shall find outer doc comments in `allowed positions`_ as specified by the Rust language:

- All item_ declarations
- Most statements
- Block expressions, but only when they are the outer expression of an
  expression statement or the final expression of another block expression.
- Enum variants, struct and union fields
- Generic lifetime or type parameter
- Expressions in limited situations
- Function, closure and function pointer parameters

.. _allowed positions: https://doc.rust-lang.org/reference/attributes.html#r-attributes.allowed-position
.. _item: https://doc.rust-lang.org/reference/items.html#r-items.syntax
<<<
RELATIONS:
- TYPE: Parent
  VALUE: SDOC-SRS-177

[[/SECTION]]

[REQUIREMENT]
MID: bdeda4b89d82446281e2c7c2eae46708
UID: SDOC-SRS-143
STATUS: Active
TITLE: Link requirements with test files and test reports
STATEMENT: >>>
StrictDoc shall support bi-directional linking between requirements, test files, and test reports.
<<<
RATIONALE: >>>
Tracing requirements to not just test files but also the test report information closes the verification cycle more completely.
<<<

[REQUIREMENT]
MID: aefeb5b89d82446281e2c7c2eae12345
UID: SDOC-SRS-144
STATUS: Active
TITLE: Link requirements with code coverage information
STATEMENT: >>>
StrictDoc shall support linking between requirements, source files, and code coverage information.
<<<
RATIONALE: >>>
Tracing requirements to not just test files but also to the code coverage information closes the verification cycle more completely.
<<<

[[SECTION]]
MID: 5fedbaba39d24da79d074501198ff654
TITLE: Forward linking from requirements to source code

[REQUIREMENT]
MID: 21637d9bec434d32bb6b97ba5a4e70e6
UID: SDOC-SRS-145
TITLE: SDoc markup's forward relations
STATEMENT: >>>
StrictDoc shall support forward linking from SDoc nodes to source files.
<<<
RATIONALE: >>>
There are cases when it is not possible to modify source code directly. The forward linking enables to refer to the files or their parts from SDoc nodes. Depending on a project structure, the forward linking from requirements to source files can replace the backward linking from source code back to requirements, or both approaches can co-exist.
<<<

[[/SECTION]]

[[SECTION]]
MID: 9c1dd6cbabd44ac680985c403cf710a7
TITLE: Source code markup – Relations

[REQUIREMENT]
MID: b9144222a7f3454da2989f494cd9647c
UID: SDOC-SRS-34
STATUS: Active
TITLE: Relation markers syntax
STATEMENT: >>>
StrictDoc shall support annotating source code with links that reference the requirements.
<<<
RELATIONS:
- TYPE: Parent
  VALUE: SDOC-SSS-72
- TYPE: File
  FORMAT: Sourcecode
  VALUE: strictdoc/backend/sdoc_source_code/grammar.py
- TYPE: File
  FORMAT: Sourcecode
  VALUE: strictdoc/backend/sdoc_source_code/reader.py
- TYPE: File
  FORMAT: Sourcecode
  VALUE: strictdoc/backend/sdoc_source_code/models/range_marker.py
- TYPE: File
  FORMAT: Sourcecode
  VALUE: strictdoc/backend/sdoc_source_code/models/source_file_info.py

[REQUIREMENT]
MID: 61c25cab106e4283b2c6d64bf1db96b2
UID: SDOC-SRS-124
STATUS: Active
TITLE: Line marker
STATEMENT: >>>
StrictDoc's shall support line markers that can be attached to single source code lines.

NOTE: A single-line marker points to a single line in a source file.
<<<
RATIONALE: >>>
Sometimes a requirement can influence only a single line in the source code. The advantage of a single-line marker compared to a range marker is that a single-line marker is not intrusive and does not clutter source code.
<<<
RELATIONS:
- TYPE: Parent
  VALUE: SDOC-SSS-72

[REQUIREMENT]
MID: 61c23c1b106e4583b2c6d64bf1d296ba
UID: SDOC-SRS-137
STATUS: Active
TITLE: Function marker
STATEMENT: >>>
StrictDoc shall support relation markers that can be attached to individual source code functions.
<<<
RATIONALE: >>>
A function is a basic building block of most programming language. It is straightforward to match a source code function to one or more related requirements.
<<<
RELATIONS:
- TYPE: Parent
  VALUE: SDOC-SSS-72

[REQUIREMENT]
MID: 86e23c1b106e4adeb2c6d64bf1d29aaa
UID: SDOC-SRS-140
STATUS: Active
TITLE: Class marker
STATEMENT: >>>
StrictDoc shall support relation markers that can be attached to source code classes.
<<<
RATIONALE: >>>
A class is a basic building block of most programming language. Some requirements can be naturally attached to the whole classes.
<<<
COMMENT: >>>
Not all programming languages support classes, e.g., C. For these languages and non-code text files, the class markers will have no effect.
<<<
RELATIONS:
- TYPE: Parent
  VALUE: SDOC-SSS-72

[REQUIREMENT]
MID: 82345cab106e4283b2c7774bf1db96b1
UID: SDOC-SRS-139
STATUS: Active
TITLE: File marker
STATEMENT: >>>
StrictDoc's shall support file markers that can be attached to entire source files.
<<<
RATIONALE: >>>
There are cases when a requirement can be attached to an entire file.
<<<
RELATIONS:
- TYPE: Parent
  VALUE: SDOC-SSS-72

[REQUIREMENT]
MID: 11c23c1b105e4583b2c6d64bf1d296cc
UID: SDOC-SRS-138
STATUS: Active
TITLE: Range marker
STATEMENT: >>>
StrictDoc shall support relation markers that can be attached to source code ranges.

NOTE: Compared to other marker types, to indicate a range, two markers are needed: one to start a range and one to end a range.
<<<
RATIONALE: >>>
There are cases when a requirement implementation results in the requirement affecting only a range/block of source code.
<<<
RELATIONS:
- TYPE: Parent
  VALUE: SDOC-SSS-72

[[/SECTION]]

[[SECTION]]
MID: 5ce2ea410dd94927807a258f482483a5
TITLE: Source code markup – Nodes

[REQUIREMENT]
MID: f44df3c6a84f4b4e9201a61023446d9c
UID: SDOC-SRS-141
STATUS: Active
TITLE: Parse nodes from source code
STATEMENT: >>>
StrictDoc shall support parsing nodes from source code.
<<<
RATIONALE: >>>
It can be practical to define the requirement and other nodes directly in source comments and then let a requirements tool generate documents from these nodes' content automatically.

A reference example: Generating test specifications from the TEST_SPEC nodes which are defined directly in source code comments.
<<<

[[/SECTION]]

[[/SECTION]]

[[SECTION]]
MID: 1acdd6ddf9d24dbaa320230402152226
UID: SECTION-SRS-Export-import-formats
TITLE: Export/import formats

[[SECTION]]
MID: ce1d174a4d794250931a5ba519583be6
UID: SECTION-SRS-RST
TITLE: RST

[REQUIREMENT]
MID: 2aa615b9cf264e7aad826f4ff466e514
UID: SDOC-SRS-70
STATUS: Active
TITLE: Export to RST
STATEMENT: >>>
StrictDoc shall allow exporting SDoc content to the RST format.
<<<
RATIONALE: >>>
Exporting SDoc content to RST enables:

1) Generating RST to Sphinx HTML documentation.
2) Generating RST to PDF using Sphinx/LaTeX.
<<<
RELATIONS:
- TYPE: Parent
  VALUE: DO178-5
- TYPE: Parent
  VALUE: DO178-16
- TYPE: File
  FORMAT: Sourcecode
  VALUE: strictdoc/export/rst/document_rst_generator.py
- TYPE: File
  FORMAT: Sourcecode
  VALUE: strictdoc/export/rst/writer.py
- TYPE: File
  FORMAT: Sourcecode
  VALUE: strictdoc/export/rst/rst_templates.py
- TYPE: File
  FORMAT: Sourcecode
  VALUE: strictdoc/export/rst/templates/requirement.jinja.rst

[REQUIREMENT]
MID: 6faffbd1d4cc47ea88c08ef38966e5ec
UID: SDOC-SRS-71
STATUS: Active
TITLE: Docutils
STATEMENT: >>>
StrictDoc shall generate RST markup to HTML using Docutils.
<<<
RATIONALE: >>>
Docutils is the most mature RST-to-HTML converter.
<<<
COMMENT: >>>
TBD: Move this to design decisions.
<<<
RELATIONS:
- TYPE: Parent
  VALUE: DO178-5
- TYPE: Parent
  VALUE: DO178-16
- TYPE: File
  VALUE: strictdoc/export/rst/rst_to_html_fragment_writer.py

[[/SECTION]]

[[SECTION]]
MID: a906dfb776334b8985f778f0fe1b79e4
UID: SECTION-SRS-ReqIF
TITLE: ReqIF

[REQUIREMENT]
MID: 2bf94015818e4770b2b1947b5fdbb969
UID: SDOC-SRS-72
STATUS: Active
TITLE: Export/import from/to ReqIF
STATEMENT: >>>
StrictDoc shall support exporting/importing requirements content from/to ReqIF format.
<<<
RELATIONS:
- TYPE: Parent
  VALUE: SDOC-SSS-58

[REQUIREMENT]
MID: bb52b698d7a544aca420d606e4e51356
UID: SDOC-SRS-73
STATUS: Active
TITLE: Standalone ReqIF layer
STATEMENT: >>>
StrictDoc shall maintain the core ReqIF implementation as a separate software component.
<<<
RATIONALE: >>>
ReqIF is a well-defined standard which exists independently of StrictDoc's development. It is reasonable to maintain the ReqIF codebase as a separate software component to allow independent development and easier maintainability.
<<<
RELATIONS:
- TYPE: Parent
  VALUE: SDOC-SSS-90

[[/SECTION]]

[[SECTION]]
MID: 0ffda51372b641f6ba460bf5ac8b3627
UID: SECTION-SRS-Excel
TITLE: Excel and CSV

[REQUIREMENT]
MID: f7b587f66dda402dbd58768e2740742f
UID: SDOC-SRS-74
STATUS: Active
TITLE: Export to Excel
STATEMENT: >>>
StrictDoc shall allow exporting SDoc documents to Excel, one Excel sheet per document.
<<<
RELATIONS:
- TYPE: Parent
  VALUE: SDOC-SSS-60
- TYPE: File
  FORMAT: Sourcecode
  VALUE: strictdoc/backend/excel/export/excel_generator.py
- TYPE: File
  FORMAT: Sourcecode
  VALUE: tests/integration/features/excel/export/20_excel_export_multiple_docs/test.itest

[REQUIREMENT]
MID: 97b587f66dda402dbd58768e2740742f
UID: SDOC-SRS-152
STATUS: Active
TITLE: Import from Excel
STATEMENT: >>>
StrictDoc shall allow importing Excel documents to SDoc documents, one Excel sheet per document.
<<<
RELATIONS:
- TYPE: Parent
  VALUE: SDOC-SSS-60
- TYPE: File
  FORMAT: Sourcecode
  VALUE: strictdoc/backend/excel/export/excel_generator.py
- TYPE: File
  FORMAT: Sourcecode
  VALUE: tests/integration/features/excel/export/20_excel_export_multiple_docs/test.itest

[REQUIREMENT]
MID: 5aa75848972249d5bec8a40812b99d86
UID: SDOC-SRS-134
STATUS: Active
TITLE: Selected fields export
STATEMENT: >>>
StrictDoc Excel export shall allow exporting SDoc documents to Excel with only selected fields.
<<<
RELATIONS:
- TYPE: Parent
  VALUE: SDOC-SSS-60
- TYPE: File
  VALUE: tests/integration/features/excel/export/03_custom_fields_to_export/test.itest

[[/SECTION]]

[[/SECTION]]

[[SECTION]]
MID: 53cfa6296eec45479544e6c5165d7fb9
UID: SECTION-SRS-Command-line-interface
TITLE: Command-line interface

[[SECTION]]
MID: 63373c3875404f1c820add84ea057c73
TITLE: General CLI requirements

[REQUIREMENT]
MID: 598647eed3a446fe93e2c54b197f830e
UID: SDOC-SRS-103
STATUS: Active
TITLE: Command-line interface
STATEMENT: >>>
StrictDoc shall provide a command-line interface.
<<<
RELATIONS:
- TYPE: Parent
  VALUE: SDOC-SSS-32
- TYPE: File
  FORMAT: Sourcecode
  VALUE: strictdoc/cli/main.py
- TYPE: File
  FORMAT: Sourcecode
  VALUE: strictdoc/cli/cli_arg_parser.py

[[/SECTION]]

[[SECTION]]
MID: 7c6a0efe76b84dcd842ef371796e787e
UID: SECTION-SRS-Command-Manage
TITLE: Command: Manage

[[SECTION]]
MID: bea76afe9bf241eaaf5984b54e00ff76
UID: SECTION-SRS-Command-Auto-UID
TITLE: Command: Auto UID

[REQUIREMENT]
MID: 7daa1310876a421f8e39f8ac25b99c1d
UID: SDOC-SRS-85
STATUS: Active
TITLE: Auto-generate requirements UIDs
STATEMENT: >>>
StrictDoc shall allow automatic generation of requirements UIDs.
<<<
RELATIONS:
- TYPE: Parent
  VALUE: SDOC-SSS-6

[[/SECTION]]

[[/SECTION]]

[[/SECTION]]

[[SECTION]]
MID: a0ed7cdd06ec4f0ab6d3ba56cced8c7e
TITLE: Python API

[REQUIREMENT]
MID: a20c5b6a021f4dd5a5a5dda2880c1b87
UID: SDOC-SRS-125
STATUS: Active
TITLE: StrictDoc Python API
STATEMENT: >>>
StrictDoc shall provide a Python API for its core functions:

- Reading SDoc files
- Creating traceability graph
- Generating HTML exports
- Converting SDoc to other formats.
<<<
RELATIONS:
- TYPE: Parent
  VALUE: SDOC-SSS-79
- TYPE: Parent
  VALUE: SDOC-SSS-86
- TYPE: Parent
  VALUE: SDOC-SSS-87

[[/SECTION]]

[[SECTION]]
MID: 590121ded2074757aa1720b4d8013426
TITLE: Web server

[REQUIREMENT]
MID: 409f462f1f4645c8ad24980727a72521
UID: SDOC-SRS-126
STATUS: Active
TITLE: Web server
STATEMENT: >>>
StrictDoc shall provide a web server.
<<<
RATIONALE: >>>
A web server is a precondition for StrictDoc's web interface. A web server can be available to a single user on their local machine or it can be deployed to a network and be made accessible by several computers.
<<<
RELATIONS:
- TYPE: Parent
  VALUE: SDOC-SSS-83

[[/SECTION]]

[[SECTION]]
MID: 44eb09d0e5b542d5984d234167e6f337
TITLE: User experience

[REQUIREMENT]
MID: 2bfb3703b218411b87864733bffb59cf
UID: SDOC-SRS-163
STATUS: Active
TITLE: StrictDoc identification
STATEMENT: >>>
StrictDoc shall provide 'about' and 'version' commands that display the project's title, current version, license, and links to the project's web pages.
<<<
RELATIONS:
- TYPE: Parent
  VALUE: SDOC-SSS-97

[[SECTION]]
MID: 821c01118a9643a188a4ecc5b0cec6a5
UID: SECTION-SSRS-Strict-mode-by-default
TITLE: Strict mode by default

[REQUIREMENT]
MID: c4e9dce647654deeab8471d04573f8cb
UID: SDOC-SRS-6
STATUS: Active
TITLE: Warnings are errors
STATEMENT: >>>
StrictDoc's default mode of operation shall treat all warnings as errors.
<<<
RATIONALE: >>>
When warnings are treated as errors, the user becomes aware of potential issues as soon as they appear.
<<<
RELATIONS:
- TYPE: Parent
  VALUE: SDOC-SSS-78

[[/SECTION]]

[[/SECTION]]

[[SECTION]]
MID: 40e7bd8aabdf4cb889e9d7b01b8729e6
UID: SECTION-SRS-Configurability
TITLE: Configurability

[REQUIREMENT]
MID: da446e6d3c6d4b13badd4a47bdbcc5a3
UID: SDOC-SRS-37
STATUS: Active
TITLE: strictdoc.toml file
STATEMENT: >>>
StrictDoc shall support a configuration of project-level options through a TOML file named ``strictdoc.toml``.
<<<
RELATIONS:
- TYPE: File
  FORMAT: Sourcecode
  VALUE: strictdoc/core/project_config.py
- TYPE: Parent
  VALUE: SDOC-SSS-92

[REQUIREMENT]
MID: a6e70c0619204a26b135d1e5fca45dd7
UID: SDOC-SRS-39
STATUS: Active
TITLE: Feature toggles
STATEMENT: >>>
StrictDoc shall allow a user to select a subset of StrictDoc's available features by listing them in the ``strictdoc.toml`` file.
<<<
RELATIONS:
- TYPE: Parent
  VALUE: SDOC-SSS-92

[REQUIREMENT]
MID: a8a17295d3e24601891c7d19d5ca67d9
UID: SDOC-SRS-119
STATUS: Active
TITLE: 'Host' parameter
STATEMENT: >>>
StrictDoc shall support configuring a host/port on which the StrictDoc web server is run.
<<<
RELATIONS:
- TYPE: Parent
  VALUE: DO178-8

[[/SECTION]]

[[SECTION]]
MID: bb14fb2c46f34cf1a82b417b57e95853
UID: SECTION-SSRS-Performance
TITLE: Performance

[REQUIREMENT]
MID: acd97ca6b9d2451da53168917d96705e
UID: SDOC-SRS-1
STATUS: Active
TITLE: Process-based parallelization
STATEMENT: >>>
StrictDoc shall support process-based parallelization for time-critical tasks.
<<<
RATIONALE: >>>
Process-based parallelization can provide a good speed-up when several large documents have to be generated.
<<<
RELATIONS:
- TYPE: Parent
  VALUE: SDOC-SSS-13
- TYPE: Parent
  VALUE: SDOC-SSS-14

[REQUIREMENT]
MID: 54602f6d120548c8bbd70d1d25113d53
UID: SDOC-SRS-95
STATUS: Active
TITLE: Caching of parsed SDoc documents
STATEMENT: >>>
StrictDoc shall implement caching of parsed SDoc documents.
<<<
RELATIONS:
- TYPE: Parent
  VALUE: SDOC-SSS-13
- TYPE: Parent
  VALUE: SDOC-SSS-14

[REQUIREMENT]
MID: 6fec2f8c0baa4ddba95bee05ad03a785
UID: SDOC-SRS-2
STATUS: Active
TITLE: Incremental generation of documents
STATEMENT: >>>
StrictDoc shall support incremental generation of documents.

NOTE: "Incremental" means that only the modified documents are regenerated when StrictDoc is run repeatedly against the same project tree.
<<<
RELATIONS:
- TYPE: Parent
  VALUE: SDOC-SSS-13
- TYPE: Parent
  VALUE: SDOC-SSS-14

[REQUIREMENT]
MID: 5f2df631605543d18d57e09bc3791003
UID: SDOC-SRS-3
STATUS: Active
TITLE: Caching of RST fragments
STATEMENT: >>>
StrictDoc shall cache the RST fragments rendered to HTML.
<<<
RATIONALE: >>>
Conversion of RST markup to HTML is a time consuming process. Caching the rendered HTML of each fragment helps to save time when rendering the HTML content.
<<<
RELATIONS:
- TYPE: Parent
  VALUE: SDOC-SSS-13
- TYPE: Parent
  VALUE: SDOC-SSS-14

[REQUIREMENT]
MID: d0c4828ed8434613aae844481bbef1ca
UID: SDOC-SRS-4
STATUS: Active
TITLE: On-demand loading of HTML pages
STATEMENT: >>>
StrictDoc's web interface shall generate the HTML content only when it is directly requested by a user.
<<<
RATIONALE: >>>
Generating a whole documentation tree for a user project can be time consuming. The on-demand loading ensures the "do less work" approach when it comes to rendering the HTML pages.
<<<
RELATIONS:
- TYPE: Parent
  VALUE: SDOC-SSS-13
- TYPE: Parent
  VALUE: SDOC-SSS-14

[REQUIREMENT]
MID: 4e014d3291ce460c993a0ff334eff4a7
UID: SDOC-SRS-5
STATUS: Active
TITLE: Precompiled Jinja templates
STATEMENT: >>>
StrictDoc shall support a precompilation of HTML templates.
<<<
RATIONALE: >>>
The StrictDoc-exported HTML content visible to a user is assembled from numerous small HTML fragments. Precompiling the HTML templates from which the content gets rendered improves the performance of the HTML rendering.
<<<
RELATIONS:
- TYPE: Parent
  VALUE: SDOC-SSS-13
- TYPE: Parent
  VALUE: SDOC-SSS-14
- TYPE: File
  FORMAT: Sourcecode
  VALUE: strictdoc/export/html/html_templates.py

[[/SECTION]]

[[SECTION]]
MID: de3a4de44f474784bf233ea7610eac6c
UID: SECTION-SRS-Quality-requirements
TITLE: Development process requirements

[[SECTION]]
MID: cbee3d3e8a9d440abaa58387c342602c
TITLE: General process

[REQUIREMENT]
MID: 27319e3866b8423099774d8770950acd
UID: SDOC-SRS-133
STATUS: Active
TITLE: Priority handling of critical issues in StrictDoc
STATEMENT: >>>
All critical issues reported in relation to StrictDoc shall be addressed with utmost priority.
<<<
RATIONALE: >>>
Prioritizing major issues ensures StrictDoc remains stable and reliable, preventing serious problems that could compromise its performance and integrity.
<<<
RELATIONS:
- TYPE: Parent
  VALUE: SDOC-SSS-78

[[/SECTION]]

[[SECTION]]
MID: 47cec130eb3d4583825355f2635e7011
UID: SECTION-SRS-Requirements-engineering
TITLE: Requirements engineering

[REQUIREMENT]
MID: d0ab977bbb494cbf818c92a1cab1bef0
UID: SDOC-SRS-128
STATUS: Active
TITLE: Requirements-based development
STATEMENT: >>>
StrictDoc's development shall be requirements-based.
<<<
RELATIONS:
- TYPE: Parent
  VALUE: SDOC-SSS-78
- TYPE: Parent
  VALUE: SDOC-SSS-76

[REQUIREMENT]
MID: b3fff332c2e342ec9dd372ebd49cb64d
UID: SDOC-SRS-91
STATUS: Active
TITLE: Self-hosted requirements
STATEMENT: >>>
StrictDoc's requirements shall be written using StrictDoc.
<<<
RELATIONS:
- TYPE: Parent
  VALUE: SDOC-SSS-50
- TYPE: Parent
  VALUE: SDOC-SSS-78

[[/SECTION]]

[[SECTION]]
MID: dfbaabc0529f4cc987358ae0563910e9
UID: SECTION-SRS-Implementation-requirements
TITLE: Implementation requirements

[[SECTION]]
MID: 5eb734a4b8944531aa75f0b71ef22d52
UID: SECTION-SRS-Programming-languages
TITLE: Programming languages

[REQUIREMENT]
MID: 4053ea6c8f6c4c29b89fea0e39912861
UID: SDOC-SRS-8
STATUS: Active
TITLE: Python language
STATEMENT: >>>
StrictDoc shall be written in Python.
<<<
RATIONALE: >>>
Python has an excellent package ecosystem. It is a widely used language. It is most often the next language for C/C++ programming community when it comes to the tools development and scripting tasks.
<<<
RELATIONS:
- TYPE: Parent
  VALUE: SDOC-SSS-69

[[/SECTION]]

[[SECTION]]
MID: 131af6457a9f43299306e6dc9fce65a7
UID: SECTION-SRS-Cross-platform-availability
TITLE: Cross-platform availability

[REQUIREMENT]
MID: ceee07bdc9bd42fc9a4d0e9b4bfc312f
UID: SDOC-SRS-9
STATUS: Active
TITLE: Linux
STATEMENT: >>>
StrictDoc shall support the Linux operating systems.
<<<
RELATIONS:
- TYPE: Parent
  VALUE: SDOC-SSS-67

[REQUIREMENT]
MID: f8c7586e1b324480ac0bd153e068350d
UID: SDOC-SRS-10
STATUS: Active
TITLE: macOS
STATEMENT: >>>
StrictDoc shall support the macOS operating system.
<<<
RELATIONS:
- TYPE: Parent
  VALUE: SDOC-SSS-67

[REQUIREMENT]
MID: 6af3dbb1e05244579622d3d2a26b5413
UID: SDOC-SRS-11
STATUS: Active
TITLE: Windows
STATEMENT: >>>
StrictDoc shall support the Windows operating system.
<<<
RELATIONS:
- TYPE: Parent
  VALUE: SDOC-SSS-67

[[/SECTION]]

[[/SECTION]]

[[SECTION]]
MID: 852396c217184ba98a0d26b92f36fd04
UID: SECTION-SRS-Implementation-constraints
TITLE: Implementation constraints

[REQUIREMENT]
MID: 83d5c896004948b48c3597d58267dafa
UID: SDOC-SRS-89
STATUS: Active
TITLE: Use of open source components
STATEMENT: >>>
StrictDoc shall be built using only open source software components.
<<<
RATIONALE: >>>
No commercial/proprietary dependency chain ensures that StrictDoc remain free and open for everyone.
<<<
RELATIONS:
- TYPE: Parent
  VALUE: DO178-7
- TYPE: Parent
  VALUE: SDOC-SSS-39
- TYPE: File
  VALUE: pyproject.toml

[REQUIREMENT]
MID: b22bf982e73246a79a5ba4ae653d21e5
UID: SDOC-SRS-14
STATUS: Active
TITLE: No heavy UI frameworks
STATEMENT: >>>
StrictDoc shall avoid using large and demanding UI frameworks.

NOTE: An example of frameworks that require a very specific architecture: React JS, AngularJS.
<<<
RELATIONS:
- TYPE: Parent
  VALUE: SDOC-SSS-90

[REQUIREMENT]
MID: 309e4108c1fa47e99d4331af642f3b81
UID: SDOC-SRS-15
STATUS: Active
TITLE: No use of NPM
STATEMENT: >>>
StrictDoc shall avoid extending its infrastructure with anything based on NPM-ecosystem.
<<<
RATIONALE: >>>
StrictDoc already deals with the Python/Pip/Pypi ecosystem. The amount of necessary maintenance is already quite high. NPM is known for splitting its projects into very small parts, which increases the complexity of maintaining all dependencies.
<<<
RELATIONS:
- TYPE: Parent
  VALUE: SDOC-SSS-90

[REQUIREMENT]
MID: b9cacb97a045418385c7f870b23ac063
UID: SDOC-SRS-16
STATUS: Active
TITLE: No use of JavaScript replacement languages (e.g., Typescript)
STATEMENT: >>>
StrictDoc shall avoid using JavaScript-based programming languages.
<<<
RATIONALE: >>>
The development team does not have specific experience with any of the JS alternatives. Staying with a general subset of JavaScript is a safer choice.
<<<
RELATIONS:
- TYPE: Parent
  VALUE: SDOC-SSS-90

[REQUIREMENT]
MID: 70f05a744a0546909dc5b69de88ad41f
UID: SDOC-SRS-87
STATUS: Active
TITLE: Monolithic application with no microservices
STATEMENT: >>>
StrictDoc shall avoid using microservices and microservice-based architectures.
<<<
RATIONALE: >>>
The project is too small to scale to a multi-service architecture.
<<<
COMMENT: >>>
This requirement could be re-considered only if a significant technical pressure
would require the use of microservices.
<<<
RELATIONS:
- TYPE: Parent
  VALUE: SDOC-SSS-82

[REQUIREMENT]
MID: 7d68821750a54cb5833b608cfc278f47
UID: SDOC-SRS-88
STATUS: Active
TITLE: No reliance on containerization
STATEMENT: >>>
StrictDoc shall avoid using containers and containerization technologies.
<<<
RATIONALE: >>>
Containers are significant extra layer of complexity. They are hard to debug.
<<<
COMMENT: >>>
This constraint does not block a StrictDoc user from wrapping StrictDoc into their containers.
<<<
RELATIONS:
- TYPE: Parent
  VALUE: SDOC-SSS-82

[[/SECTION]]

[[SECTION]]
MID: e4e5b9934e074cdb9567fa197db20a4a
UID: SECTION-SRS-Coding-constraints
TITLE: Coding constraints

[REQUIREMENT]
MID: 61d96cd1d03e40c48187ee67ac0b65f6
UID: SDOC-SRS-40
STATUS: Active
TITLE: Use of asserts
STATEMENT: >>>
StrictDoc's development shall ensure a use of assertions throughout the project codebase.

NOTE: At a minimum, the function input parameters must be checked for validity.
<<<
RELATIONS:
- TYPE: Parent
  VALUE: SDOC-SSS-78

[REQUIREMENT]
MID: 72b5b0c925cf4ef49749b7e466675df1
UID: SDOC-SRS-41
STATUS: Active
TITLE: Use of type annotations in Python code
STATEMENT: >>>
StrictDoc's development shall ensure a use of type annotations throughout the project's Python codebase.
<<<
RELATIONS:
- TYPE: Parent
  VALUE: SDOC-SSS-78

[[/SECTION]]

[[SECTION]]
MID: 61e87567580045378d970b327d218cac
UID: SECTION-SRS-Linting
TITLE: Linting

[REQUIREMENT]
MID: 6c0163c56ade49faa353ec06cbd676cd
UID: SDOC-SRS-42
STATUS: Active
TITLE: Compliance with Python community practices (PEP8 etc)
STATEMENT: >>>
StrictDoc's development shall ensure that the project's codebase is compliant with the Python community's modern practices.
<<<
RELATIONS:
- TYPE: Parent
  VALUE: SDOC-SSS-90

[[/SECTION]]

[[SECTION]]
MID: 3029f97a1276499dbbd5d7c71691908e
UID: SECTION-SRS-Static-analysis
TITLE: Static analysis

[REQUIREMENT]
MID: 2cc9b494ca6248058b6bf63b6e2c1cfa
UID: SDOC-SRS-43
STATUS: Active
TITLE: Static type checking
STATEMENT: >>>
StrictDoc's development shall include a continuous type checking of StrictDoc's codebase.
<<<
RELATIONS:
- TYPE: Parent
  VALUE: SDOC-SSS-78
- TYPE: File
  VALUE: tasks.py

[[/SECTION]]

[[SECTION]]
MID: 3aba8ca86d404ba9a063ce125489f35b
UID: SECTION-SRS-Testing
TITLE: Testing

[REQUIREMENT]
MID: 2731c64ab32146eeb4b8167df4a34540
UID: SDOC-SRS-44
STATUS: Active
TITLE: Unit testing
STATEMENT: >>>
StrictDoc's development shall provide unit testing of its codebase.
<<<
RELATIONS:
- TYPE: Parent
  VALUE: SDOC-SSS-77
- TYPE: Parent
  VALUE: SDOC-SSS-78

[REQUIREMENT]
MID: 70ef3986cfc4437bbb10288d3b55958c
UID: SDOC-SRS-45
STATUS: Active
TITLE: CLI interface black-box integration testing
STATEMENT: >>>
StrictDoc's development shall provide complete black-box integration testing of its command-line interface.
<<<
RELATIONS:
- TYPE: Parent
  VALUE: SDOC-SSS-77
- TYPE: Parent
  VALUE: SDOC-SSS-78

[REQUIREMENT]
MID: a42c65f1a53b4c9bb50bc2a1ecb855cb
UID: SDOC-SRS-46
STATUS: Active
TITLE: Web end-to-end testing
STATEMENT: >>>
StrictDoc's development shall provide complete end-to-end testing of the web interface.
<<<
RELATIONS:
- TYPE: Parent
  VALUE: SDOC-SSS-77
- TYPE: Parent
  VALUE: SDOC-SSS-78

[REQUIREMENT]
MID: c90f35ab9a7f4c29a418557151878b9f
UID: SDOC-SRS-47
STATUS: Active
TITLE: At least one integration or end-to-end test
STATEMENT: >>>
Every update to the StrictDoc codebase shall be complemented with a corresponding provision of at least one test as follows:

- For web interface: at least one end-to-end test.
- For command-line interface: at least one black-box integration test.
- For internal Python functions: at least one unit test.

NOTE: This requirement implies that no modifications to StrictDoc's functionality can be merged unless accompanied by at least one test.
<<<
RATIONALE: >>>
This requirement ensures that every new feature or a chance in the codebase is covered/stressed by at least one test, according to the change type.
<<<
RELATIONS:
- TYPE: Parent
  VALUE: SDOC-SSS-77
- TYPE: Parent
  VALUE: SDOC-SSS-78

[[/SECTION]]

[[/SECTION]]

[[SECTION]]
MID: 83bdb9731e78431cb48d584d279443b4
TITLE: Code hosting and distribution

[[SECTION]]
MID: dbd186fae9624fd6af8aeb55edfaa43b
UID: SECTION-SRS-Code-hosting
TITLE: Code hosting

[REQUIREMENT]
MID: b112c60bc2f34114ab1f3361a1a10a00
UID: SDOC-SRS-12
STATUS: Active
TITLE: GitHub
STATEMENT: >>>
StrictDoc's source code shall be hosted on GitHub.
<<<
RELATIONS:
- TYPE: Parent
  VALUE: SDOC-SSS-38
- TYPE: Parent
  VALUE: SDOC-SSS-82

[[/SECTION]]

[REQUIREMENT]
MID: bd949cbbe07c4cb29492ea0c8e5c1eec
UID: SDOC-SRS-118
STATUS: Active
TITLE: StrictDoc license
STATEMENT: >>>
All StrictDoc software shall be licensed under the Apache 2 license.
<<<
RELATIONS:
- TYPE: Parent
  VALUE: SDOC-SSS-40
- TYPE: File
  VALUE: LICENSE
- TYPE: File
  VALUE: NOTICE

[[/SECTION]]
