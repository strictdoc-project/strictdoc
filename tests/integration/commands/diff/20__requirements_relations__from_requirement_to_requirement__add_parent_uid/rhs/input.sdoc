[DOCUMENT]
TITLE: Hello world doc

[REQUIREMENT]
UID: REQ-1
TITLE: Requirement #1
STATEMENT: System shall do 1.

[REQUIREMENT]
UID: REQ-2
TITLE: Requirement #2
STATEMENT: System shall do 2.
RELATIONS:
- TYPE: Parent
  VALUE: REQ-1
