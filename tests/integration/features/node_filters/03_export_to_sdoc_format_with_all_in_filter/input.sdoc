[DOCUMENT]
TITLE: Query filter all list membership

[REQUIREMENT]
TAGS: tag_b, tag_a
TITLE: Requirement #1
STATEMENT: Statement #1

[REQUIREMENT]
TAGS: tag_a
TITLE: Requirement #2
STATEMENT: Statement #2

[REQUIREMENT]
TAGS: tag_b
TITLE: Requirement #3
STATEMENT: Statement #3
