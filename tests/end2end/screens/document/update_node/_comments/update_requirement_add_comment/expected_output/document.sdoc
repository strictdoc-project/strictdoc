[DOCUMENT]
TITLE: Document 1

[REQUIREMENT]
TITLE: Requirement title
STATEMENT: >>>
Requirement statement.
<<<
RATIONALE: >>>
Requirement rationale.
<<<
COMMENT: >>>
Comment #1
<<<
COMMENT: >>>
Comment #2
<<<
COMMENT: >>>
Comment #3
<<<
