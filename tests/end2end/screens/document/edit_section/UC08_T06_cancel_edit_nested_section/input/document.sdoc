[DOCUMENT]
TITLE: Document 1

[FREETEXT]
Hello world!
[/FREETEXT]

[SECTION]
TITLE: Section 1

[FREETEXT]
This is a free text of the section 1.
[/FREETEXT]

[SECTION]
TITLE: Section 1.1

[FREETEXT]
This is a free text of the section 1.1.
[/FREETEXT]

[/SECTION]

[/SECTION]
