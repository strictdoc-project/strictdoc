[DOCUMENT]
TITLE: Test document 54
UID: DOC-54
OPTIONS:
  VIEW_STYLE: Plain

[[SECTION]]
TITLE: Section 1

[TEXT]
STATEMENT: >>>
Vivamus consectetur mollis varius. Quisque posuere venenatis nulla, sit amet pulvinar metus vestibulum **sed**. Sed at libero nec justo leo.
<<<

[[/SECTION]]

[[SECTION]]
TITLE: Section 2

[TEXT]
STATEMENT: >>>
Lorem ipsum dolor sit amet, consectetur adipiscing elit. Donec a diam lectus. Sed sit amet ipsum mauris. Maecenas congue ligula ac quam viverra nec consectetur ante hendrerit. Donec et mollis dolor.
<<<

[[/SECTION]]
